/*
Copyright (C) 2013-2017 Huawei Technologies Co., Ltd. All rights reserved.
*/
submodule huawei-arp-action {
  belongs-to huawei-arp {
    prefix arp;
  }
  import huawei-pub-type {
    prefix pub-type;
  }
  import ietf-inet-types {
    prefix inet;
  }
  include huawei-arp-type;
  
  organization
    "Huawei Technologies Co.,Ltd.";
  contact
    "Huawei Industrial Base Bantian, Longgang Shenzhen 518129                    
        People's Republic of China                    
        Website: http://www.huawei.com Email: support@huawei.com";
  description
    "ARP action.";
  revision 2017-03-23 {
    description
      "Functions supported by the schema are added to the YANG file.";
    reference
      "Huawei private.";
  }
  revision 2013-01-01 {
    description
      "Init revision";
    reference
      "Huawei private.";
  }
  rpc clearArp {
    description
      "Clear ARP entries by type.";
    input {
      leaf clearArpType {
        type arpClearArpType;
        default "ClearDynamicArp";
        description
          "Types of ARP entries to be cleared. The available options are dynamic and remote backup ARP entries.";
      }
    }
  }
  rpc clearArpByIfName {
    description
      "Clear ARP entries on an interface. Currently, only dynamic ARP entries on an interface can be cleared.";
    input {
      leaf ifName {
        type pub-type:ifName;
        mandatory true;
        description
          "Name of an interface where ARP entries to be cleared reside.";
      }
      leaf ipAddrValue {
        type inet:ipv4-address-no-zone;
        description
          "IP address with which the ARP entries are to be cleared.";
      }
    }
  }
  rpc clearArpByVpn {
    description
      "Clear dynamic ARP entries by VPN instance.";
    input {
      leaf vrfName {
        type pub-type:vrfName;
        mandatory true;
        description
          "Name of the VPN instance where the ARP entries to be cleared reside.";
      }
    }
  }
  rpc resetAllStatistics {
    description
      "Clear all ARP statistics.";
  }
  rpc resetStatistics {
    description
      "Clear ARP statistics based on specific conditions. Currently, ARP statistics can be cleared only based on the Slot ID.";
    input {
      leaf slotId {
        type string {
          length "1..24";
        }
        description
          "Slot ID of the interface board where ARP statistics to be cleared reside.";
      }
    }
  }
  rpc resetAllIfStat {
    description
      "Clear ARP statistics on all interfaces.";
  }
  rpc resetIfStat {
    description
      "Clear ARP statistics on an interface.";
    input {
      leaf ifName {
        type pub-type:ifName;
        mandatory true;
        description
          "Name of an interface where ARP statistics to be cleared reside.";
      }
    }
  }
}
