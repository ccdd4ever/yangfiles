/*
Copyright (C) 2013-2017 Huawei Technologies Co., Ltd. All rights reserved.
*/
submodule huawei-bgp-bgpcomm {
  belongs-to huawei-bgp {
    prefix bgp;
  }
  import huawei-pub-type {
    prefix pub-type;
  }
  import huawei-l3vpn {
    prefix l3vpn;
  }
  import huawei-ifm {
    prefix ifm;
  }
  import huawei-rtp {
    prefix rtp;
  }
  import huawei-acl {
    prefix acl;
  }
  import ietf-inet-types {
    prefix inet;
  }
  import ietf-yang-types {
    prefix yang;
  }
  import huawei-extension {
    prefix ext;
  }
  include huawei-bgp-type;
  
  organization
    "Huawei Technologies Co.,Ltd.";
  contact
    "Huawei Industrial Base Bantian, Longgang Shenzhen 518129                    
        People's Republic of China                    
        Website: http://www.huawei.com Email: support@huawei.com";
  description
    "Description of submodule bgp_bgpcomm";
  revision 2017-03-23 {
    description
      "Functions supported by the schema are added to the YANG file.";
    reference
      "Huawei private.";
  }
  revision 2013-01-01 {
    description
      "Init revision";
    reference
      "Huawei private.";
  }
  grouping bgp_bgpcomm_bgpcomm_type {
    description
      "";
    container bgpSite {
      description
        "Site containing the global BGP information, such as the protocol version, AS number, and system identifier.";
      leaf bgpVersion {
        type uint8;
        config false;
        description
          "BGP version, which is BGP-4 at present. BGP-4 provides a new mechanism to support Classless Inter-Domain Routing (CIDR). In this case, the network prefix-based advertisement is supported and the concept of class for a BGP network is canceled in the network prefix-supported advertisements. Another mechanism is also introduced to support route summarization, including the summarization of AS paths.";
      }
      leaf bgpEnable {
        type boolean;
        default "false";
        description
          "Enable BGP. By default, BGP is disabled.";
      }
      leaf asNumber {
        when "not(../bgpEnable='false')";
        type asNumberValidate {
          length "1..11";
          pattern '((([1-9]\d{0,8})|([1-3]\d{9})|(4[0-1]\d{8})|(42[0-8]\d{7})|(429[0-3]\d{6})|(4294[0-8]\d{5})|(42949[0-5]\d{4})|(429496[0-6]\d{3})|(4294967[0-1]\d{2})|(42949672[0-8]\d{1})|(429496729[0-5]))|((([1-9]\d{0,3})|([1-5]\d{4})|(6[0-4]\d{3})|(65[0-4]\d{2})|(655[0-2]\d)|(6553[0-5]))[\.](([0-9]\d{0,3})|([1-5]\d{4})|(6[0-4]\d{3})|(65[0-4]\d{2})|(655[0-2]\d)|(6553[0-5]))))';
        }
        description
          "Local AS number, which can be in either of the two formats:
The two-byte format is X. X is an integer ranging from 1 to 65535.
The four-byte format is X.Y and X. When the format is X.Y, X and Y are both integers, with the value of X ranging from 1 to 65535, and the value of Y ranging from 0 to 65535; when the format is X, X is an interger, with the value ranging from 1 to 4294967295.
An AS consists of multiple routers managed based on the same techniques. Interior Gateway Protocol (IGP) and universal routing metric packets are used inside an AS, and Exterior Gateway Protocol (EGP) is used outside to send packets to other ASs. With the development of this definition, one AS usually uses multiple IGPs and metrics. Even though multiple IGPs and metrics are used, the routing plan and destination reachability of an AS are consistent with those of another AS.";
        ext:allowDelete "true";
      }
      leaf gracefulRestart {
        type boolean;
        must "not(../bgpEnable='false')";
        default "false";
        description
          "Enable GR of the BGP speaker in the specified address family, peer address, or peer group. When GR is enabled, the BGP speaker enabled with GR keeps the forwarding state and sends the End-Of-RIB flag during the restart. In this case, however, the BGP speaker may not maintain the forwarding table. Enabling or disabling GR may delete and re-establish all sessions and instances.";
      }
      leaf timeWaitForRib {
        when "../gracefulRestart='true'";
        type uint32 {
          range "3..3000";
        }
        default "600";
        description
          "Period of waiting for the End-Of-RIB flag. The value is an integer in seconds. The default value is 600. When a BGP session is established or re-established, the router enabled with GR should receive the End-Of-RIB flag in this period. If the router does not receive the End-Of-RIB flag in this period, ensure that the router can exit from the GR process.";
        ext:allowDelete "true";
      }
      leaf asPathLimit {
        type uint16 {
          range "1..2000";
        }
        must "not(../bgpEnable='false')";
        description
          "Maximum number of AS numbers in the AS_Path attribute. The default value is 255.";
        ext:allowDelete "true";
      }
      leaf checkFirstAs {
        type boolean;
        must "not(../bgpEnable='false')";
        default "true";
        description
          "Check the first AS in the AS_Path of the update messages from EBGP peers. By default, this function is enabled.";
      }
      leaf confedIdNumber {
        type asNumberValidate {
          length "1..11";
          pattern '((([1-9]\d{0,8})|([1-3]\d{9})|(4[0-1]\d{8})|(42[0-8]\d{7})|(429[0-3]\d{6})|(4294[0-8]\d{5})|(42949[0-5]\d{4})|(429496[0-6]\d{3})|(4294967[0-1]\d{2})|(42949672[0-8]\d{1})|(429496729[0-5]))|((([1-9]\d{0,3})|([1-5]\d{4})|(6[0-4]\d{3})|(65[0-4]\d{2})|(655[0-2]\d)|(6553[0-5]))[\.](([0-9]\d{0,3})|([1-5]\d{4})|(6[0-4]\d{3})|(65[0-4]\d{2})|(655[0-2]\d)|(6553[0-5]))))';
        }
        must "not(../bgpEnable='false')";
        description
          "Confederation ID.";
        ext:allowDelete "true";
      }
      leaf confedNonstanded {
        type boolean;
        must "not(../bgpEnable='false')";
        default "false";
        description
          "Configure the device to be compatible with devices in a nonstandard confederation.";
      }
      leaf bgpRidAutoSel {
        type boolean;
        must "not(../bgpEnable='false')";
        default "false";
        description
          "By default, a BGP VPN instance does not automatically select a router ID. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
1. If Loopback interfaces configured with IP addresses exist, the largest IP address among the IP addresses of the Loopback interfaces is selected as the router ID. 
2. If there is no Loopback interface configured with an IP address, the largest IP address among the IP addresses of other interfaces is selected as the router ID, regardless of whether the interface is Up.";
      }
      leaf keepAllRoutes {
        type boolean;
        must "not(../bgpEnable='false')";
        default "false";
        description
          "Save all the updated information about BGP routes from a peer or peer group after a BGP connection is established, even though these BGP routes fail to match the routing policy on the ingress. By default, only the updated information about BGP routes from a specified peer is saved on condition that the routes match the routing policy on the ingress. If a router supports route refreshing, this option is not required.";
      }
      leaf memoryLimit {
        type boolean;
        must "not(../bgpEnable='false') or (../bgpEnable='false' and ../memoryLimit='false')";
        default "false";
        description
          "Support BGP RIB memory protection. By default, the function is not enabled. With BGP RIB memory protection, routes are no longer received after the RIB memory is overloaded.";
      }
      leaf grPeerReset {
        when "../gracefulRestart='true'";
        type boolean;
        default "false";
        description
          "Peer disconnection through GR.";
      }
      leaf isShutdown {
        type boolean;
        default "false";
        description
          "Interrupt BGP all neighbor";
      }
      leaf suppressInterval {
        type uint32 {
          range "1..65535";
        }
        default "60";
        description
          "Specifies the reference period used to add penalty in case of next hop flapping in seconds. By default, the value is 60 seconds.";
        ext:allowDelete "true";
      }
      leaf holdInterval {
        type uint32 {
          range "1..65535";
        }
        default "120";
        description
          "Specifies the reference period used to hold penalty in case of next hop flapping in seconds. By default, the value is 120 seconds.";
        ext:allowDelete "true";
      }
      leaf clearInterval {
        type uint32 {
          range "1..65535";
        }
        default "600";
        description
          "Specifies the reference period used to clear penalty in case of next hop flapping in seconds. By default, the value is 600 seconds.";
        ext:allowDelete "true";
      }
      leaf restartTime {
        when "../gracefulRestart='true'";
        type uint16 {
          range "3..3600";
        }
        default "150";
        description
          "Specifies the maximum time during which a peer waits for a BGP session reestablishment. It is an integer ranging from 3 to 3600, in seconds. By default, the value is 150 seconds.";
        ext:allowDelete "true";
      }
      leaf lowestPriority {
        type boolean;
        default "false";
        description
          "Reduce route priority to lowest.";
        ext:allowDelete "true";
      }
      leaf delayTime {
        when "../lowestPriority='true'";
        type uint32 {
          range "1..864000";
        }
        description
          "Specifies the delayTime.";
        ext:allowDelete "true";
      }
    }
    container bgpConfedPeerAss {
      description
        "Confederation AS list.";
      list bgpConfedPeerAs {
        key "confedPeerAsNum";
        max-elements  "32";
        description
          "Confederation AS.";
        leaf confedPeerAsNum {
          type asNumberValidate {
            length "1..11";
            pattern '((([1-9]\d{0,8})|([1-3]\d{9})|(4[0-1]\d{8})|(42[0-8]\d{7})|(429[0-3]\d{6})|(4294[0-8]\d{5})|(42949[0-5]\d{4})|(429496[0-6]\d{3})|(4294967[0-1]\d{2})|(42949672[0-8]\d{1})|(429496729[0-5]))|((([1-9]\d{0,3})|([1-5]\d{4})|(6[0-4]\d{3})|(65[0-4]\d{2})|(655[0-2]\d)|(6553[0-5]))[\.](([0-9]\d{0,3})|([1-5]\d{4})|(6[0-4]\d{3})|(65[0-4]\d{2})|(655[0-2]\d)|(6553[0-5]))))';
          }
          description
            "Confederation AS number, which can be in either of the two formats:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
        }
      }
    }
    container bgpVrfs {
      description
        "Configure the list of all BGP instances.";
      list bgpVrf {
        key "vrfName";
        max-elements  "4096";
        description
          "Create a BGP instance.";
        leaf vrfName {
          type leafref {
            path "/l3vpn:l3vpn/l3vpn:l3vpncomm/l3vpn:l3vpnInstances/l3vpn:l3vpnInstance/l3vpn:vrfName";
          }
          description
            "Name of a BGP instance. The name is a case-sensitive string of characters. The BGP instance can be used only after the corresponding VPN instance is created. ";
        }
        leaf vrfRidAutoSel {
          when "../vrfName!='_public_'";
          type boolean;
          description
            "By default, a BGP VPN instance does not automatically select a router ID. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
1. If Loopback interfaces configured with IP addresses exist, the largest IP address among the IP addresses of the Loopback interfaces is selected as the router ID. 
2. If there is no Loopback interface configured with an IP address, the largest IP address among the IP addresses of other interfaces is selected as the router ID, regardless of whether the interface is Up.";
        }
        leaf routerId {
          type inet:ipv4-address-no-zone;
          description
            "ID of a router that is in IPv4 address format. Certain dynamic routing protocols require a router ID. If no router ID is specified for a router when these protocols are enabled, the router ID in the RM module is used by default. The default router ID in the RM module is 0.0.0.0 when the router is not configured with any interface. 
The rules for selecting a router ID are as follows:
1. If you set a router ID through this configuration, the set router ID is used. If the router ID is not set, you need to select a router ID according to the following rules:
(1) If loopback interfaces configured with IP addresses exist, the largest IP address among the IP addresses of the loopback interfaces is selected as the router ID.
(2) If no loopback interface configured with an IP address exists, the largest IP address among the IP addresses of other interfaces is selected as the router ID, regardless of whether the interface is Up.
The router ID is reselected only when the interface address that is selected as the router ID is deleted or changed. The router ID is not reselected in any of the following cases:
a. The interface is Down.
b. A loopback interface is configured when the IP address of a non-loopback interface is selected as the router ID.
c. A larger IP address of an interface is configured.
2. Each VPN instance selects the router ID from the addresses of the interfaces of the VPN instance according to the preceding rules.
3. When both the AMB and SMB exist on the router, the system backs up the router ID set through the related command and the router ID that is selected from IP addresses of the interfaces. After the active/standby switchover is performed, the system checks the validity of the router ID selected from the interface addresses. If the router ID is invalid, the system reselects a router ID.";
          ext:allowDelete "true";
        }
        leaf effectRouterId {
          type inet:ipv4-address-no-zone;
          default "0.0.0.0";
          config false;
          description
            "Router ID that takes effect.";
        }
        leaf keepaliveTime {
          when "../vrfName='_public_'";
          type uint32 {
            range "0..21845";
          }
          default "60";
          description
            "If the value of a timer changes, the BGP peer relationship between the routers is disconnected. This is because the peers need to re-negotiate the Keepalive time and hold time. Therefore, confirm the action before you change the value of the timer. The Keepalive time should be at least three times of the hold time.";
          ext:allowDelete "true";
        }
        leaf holdTime {
          when "../vrfName='_public_'";
          type uint32 {
            range "0..65535";
          }
          must "(../holdTime!=1) or (../holdTime!=2) or (../holdTime>=../keepaliveTime*3) or (../holdTime>=../minHoldTime)";
          default "180";
          description
            "Hold time, in seconds. The value of the hold time can be 0 or range from 3 to 65535. When setting keepalive-time and hold-time, note the following:
1. The values of keepalive-time and hold-time cannot both be 0. Otherwise, the BGP timer becomes invalid. That is, BGP does not detect link faults according to the timer.
2. The value of hold-time is much greater than that of keepalive-time, such as, keepalive 1 and hold 65535. If the value of hold-time is too large, BGP cannot detect link faults timely.
The priority of a timer is lower than that of a peer timer.
After a connection is established between peers, the values of keepalive-time and hold-time are negotiated by the peers. The smaller value of hold-time contained in Open packets of both peers is taken as the value of hold-time. The smaller value of the locally set value of keepalive-time and one third of the value of hold-time is taken as the value of keepalive-time.";
          ext:allowDelete "true";
        }
        leaf minHoldTime {
          when "../vrfName='_public_'";
          type uint32 {
            range "0..65535";
          }
          default "0";
          description
            "The minimum hold time is either 0 or an integer ranging from 20 to 65535, in seconds. If the value is changed, the new value takes effect since the next peer relationship establishment. During the peer relationship establishment, the local device checks the hold time of the remote end. If the hold time is less than the minimum hold time, the local device sends an error packet with error code 02 and subcode 06, and the peer relationship fails to be established.";
          ext:allowDelete "true";
        }
        leaf connRetryTime {
          when "../vrfName='_public_'";
          type uint16 {
            range "1..65535";
          }
          default "32";
          description
            "ConnectRetry interval. The value is an integer, in seconds. The default value is 32s.";
          ext:allowDelete "true";
        }
        leaf defaultAfType {
          when "../vrfName!='_public_'";
          type bgpcommVrfPrefixType;
          must "not(../vrfName!='_public_') or (../vrfName!='_public_')";
          default "ipv4uni";
          description
            "Type of a created address family, which can be IPv4 unicast or IPv6 unicast. The default type is IPv4 unicast. This option takes effect only when a BGP instance is created for the first time. ";
          ext:allowDelete "true";
        }
        container bgpPeerGroups {
          description
            "List of BGP peer groups. The BGP peer groups can help you simplify the configurations. If you want to perform the same configuration for several peers, you can create a peer group and then configure the peer group. After you add these peers to the peer group, all these peers will have the same configurations as the peer group. ";
          list bgpPeerGroup {
            key "afType groupName groupType";
            description
              "Information about a BGP peer group.";
            leaf afType {
              type bgpcommGroupAddrFamily;
              description
                "Address family type of a peer group. For a public instance, this value cannot be modified. Since a VPN instance is related to its address family, you need to specify the address family type when creating a peer group in the VPN instance. For example, if you want to create an address family in a VPN instance of IPv4 unicast, choose IPv4 unicast as the address family type.";
            }
            leaf groupName {
              type string {
                length "1..47";
                pattern '([^\? ]+)';
              }
              description
                "Specify the name of a peer group. The value is a string of characters, spaces not supported.";
            }
            leaf groupType {
              type bgpcommPeerType;
              description
                "Specify the type of a peer group. The value can be IBGP or EBGP. The default value is IBGP.";
            }
            leaf groupAs {
              when "not(../groupType='ibgp')";
              type string {
                length "1..11";
              }
              description
                "Specify the AS number of a peer group. The AS number is in either a 2-byte or 4-byte format. 
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf description {
              type string {
                length "1..255";
                pattern '([^?]*)';
              }
              description
                "Specify the description of a peer group. The value is a string, which can be letters or digits, spaces supported. By default, no description is configured.";
              ext:allowDelete "true";
            }
            leaf fakeAs {
              when "not(../groupType='ibgp')";
              type string {
                length "1..11";
              }
              description
                "Fake AS number that is specified for a local peer. By default, a peer uses the actual AS number of the local end.
An AS number can be in either two-byte format or four-byte format:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf dualAs {
              when "not(../fakeAs)";
              type boolean;
              default "false";
              description
                "By default, dual AS is not enabled, and the remote EBGP peer uses the fake AS number when specifying the AS number for a local peer. 
After dual AS is enabled, the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
            }
            leaf conventional {
              when "not(../../../vrfName!='_public_' and ../afType='ipv6uni')";
              type boolean;
              default "false";
              description
                "Enable general router functions on peers. In conventional mode, not all the extended router functions, such as, route refreshing, GR, and multi-address family negotiation, are available. Therefore, the router of a new version can be compatible with the routers of earlier versions.";
            }
            leaf routeRefresh {
              type boolean;
              default "true";
              description
                "Enable BGP to advertise Refresh messages to peers. By default, this function is enabled.";
            }
            leaf fourByteAs {
              type boolean;
              default "true";
              description
                "Enables BGP to advertise routes carrying 4-byte AS numbers to peers. By default, the function is enabled. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte.  If the 4-byte AS number function is disabled in such a situation, BGP sessions may fail to be established, and route transmission may be affected.";
            }
            leaf isIgnore {
              type boolean;
              default "false";
              description
                "Tear down sessions between peers and clear all related routing information. By default, this function is disabled.";
            }
            leaf localIfName {
              type leafref {
                path "/ifm:ifm/ifm:interfaces/ifm:interface/ifm:ifName";
              }
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
              ext:allowDelete "true";
            }
            leaf localIfAddress {
              type inet:ip-address-no-zone;
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
            }
            leaf ebgpMaxHop {
              when "not(../groupType='ibgp')";
              type uint32 {
                range "1..255";
              }
              must "not(../validTtlHops) and ../groupType='ebgp'";
              default "1";
              description
                "Maximum number of hops in an indirect EBGP connection. By default, EBGP connections can be established only between directly connected peers. The function must be configured on both ends.";
              ext:allowDelete "true";
            }
            leaf validTtlHops {
              type uint16 {
                range "1..255";
              }
              must "not(../ebgpMaxHop and ../ebgpMaxHop>1 and ../ebgpMaxHop<=255)";
              description
                "";
              ext:allowDelete "true";
            }
            leaf connectMode {
              type bgpcommPeerConnectMode;
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
              ext:allowDelete "true";
            }
            leaf isLogChange {
              type boolean;
              default "true";
              description
                "Enable BGP to record the session status and events of the specified peer or peer group. By default, the function is enabled.";
            }
            leaf pswdType {
              type bgpcommPasswordType;
              must "not(../keyChainName)";
              default "null";
              description
                "Enable BGP peers to establish a TCP connection and perform the Message Digest 5 (MD5) authentication for BGP messages. Plaintexts and ciphertexts are supported.";
              ext:allowDelete "true";
            }
            leaf pswdCipherText {
              when "not(not(../pswdType))";
              type pub-type:passwordExtend {
                length "1..432";
              }
              description
                "Enable BGP peers to establish a TCP connection and perform the Message Digest 5 (MD5) authentication for BGP messages. The character string in a password identifies the contents of the password, spaces not supported. The TCP connection can be established only when the same MD5 authentication password is set on both ends. If a plaintext is used, the maximum password length is 255. If a ciphertext is used, the maximum password length is 392. If the length is set to 0, no password is set.";
              ext:allowDelete "true";
            }
            leaf keepAliveTime {
              type uint32 {
                range "0..21845";
              }
              default "60";
              description
                "Specify the Keepalive time of a peer or peer group. The value is an integer, in seconds. If the value of a timer changes, the peers need to re-negotiate the interval value for the keepalive-time and hold-time. This disconnects the BGP peer relationship between the routers. Therefore, you need to double check whether it is a must to change the value of the timer. Ensure that the hold time is at least three times longer than the keepalive time when you configure the BGP timer.";
              ext:allowDelete "true";
            }
            leaf holdTime {
              type uint32 {
                range "0..65535";
              }
              must "(../holdTime!=1) or (../holdTime!=2) or (../holdTime>=../keepAliveTime*3) or (../holdTime>=../minHoldTime)";
              default "180";
              description
                "Specify the Hold time of a peer or peer group. The value is either 0 or an integer ranging from 0 to 65535, in seconds. When setting the timer values of keepalive-time and hold-time, avoid the following settings: 1.The interval values of keepalive-time and hold-time are both set to 0. This will cause BGP timer to become invalid, and BGP will not detect link faults based on the timer. 
2. The interval value of hold-time is much greater than that of keepalive-time. For example, the interval value of keepalive-time is 1, and that of hold-time is 65535. If the interval value of hold-time is too large, BGP will not be able to detect link faults in time. The priority of the timer configured here is lower than that of timer configured with interval values of keepalive-time and hold-time of a peer. After a connection is established between peers, the interval values of keepalive-time and hold-time are negotiated by the peers. The smaller interval value of hold-time contained in Open packets of both peers is taken as the interval value of hold-time. The smaller interval value of one third of the interval value of hold-time and the locally set interval value of keepalive-time is taken as the interval value of keepalive-time.";
              ext:allowDelete "true";
            }
            leaf minHoldTime {
              type uint32 {
                range "0..65535";
              }
              default "0";
              description
                "The minimum hold time is either 0 or an integer ranging from 20 to 65535, in seconds. If the value is changed, the new value takes effect since the next peer relationship establishment. During the peer relationship establishment, the local device checks the hold time of the remote end. If the hold time is less than the minimum hold time, the local device sends an error packet with error code 02 and subcode 06, and the peer relationship fails to be established.";
              ext:allowDelete "true";
            }
            leaf keyChainName {
              type string {
                length "1..47";
              }
              must "not(not(../pswdType))";
              description
                "Specify the Keychain authentication name used when BGP peers establish a TCP connection. The value is a string, spaces not supported. By default, the Keychain authentication is not configured. Keychain authentication mode and password authentication mode are mutually exclusive. Configuring Keychain authentication can enhance the security of the TCP connections between BGP peers. Keychain authentication using the same encryption algorithm and password must be configured on the two ends of BGP peers to establish a TCP connection and exchange BGP packets. Before configuring BGP Keychain authentication, you need to configure Keychain according to keychain name. Otherwise, the TCP connections between the BGP peers cannot be established.";
              ext:allowDelete "true";
            }
            leaf connRetryTime {
              type uint16 {
                range "1..65535";
              }
              default "32";
              description
                "ConnectRetry interval. The value is an integer, in seconds. The default value is 32s.";
              ext:allowDelete "true";
            }
            leaf tcpMSS {
              type uint16 {
                range "176..4096";
              }
              description
                "Maximum TCP MSS value used for TCP connection establishment for a peer group. ";
              ext:allowDelete "true";
            }
            leaf prependGlobalAs {
              when "not(../groupType='ibgp' or not(../fakeAs))";
              type boolean;
              default "false";
              description
                "Add the global AS number to the Update packets to be advertised.";
            }
            leaf prependFakeAs {
              when "not(../groupType='ibgp' or not(../fakeAs))";
              type boolean;
              default "false";
              description
                "Add the Fake AS number to received Update packets.";
            }
            container peerMembers {
              config false;
              description
                "List of members in a peer group.";
              list peerMember {
                key "peerSession";
                config false;
                description
                  "Member in a peer group.";
                leaf peerSession {
                  type string {
                    length "1..512";
                  }
                  config false;
                  description
                    "Specify the address of the peer joining the peer group.";
                }
              }
            }
            container peerGroupBfd {
              description
                "Configure BFD.";
              leaf multiplier {
                type uint32 {
                  range "3..50";
                }
                default "3";
                description
                  "Specify the detection multiplier. The default value is 3.";
                ext:allowDelete "true";
              }
              leaf isBfdEnable {
                type boolean;
                default "false";
                description
                  "Configure BFD.";
              }
              leaf rxInterval {
                type uint32 {
                  range "3..1000";
                }
                description
                  "Specify the minimum interval at which BFD packets are received. By default, the value is determined by the PAF file.";
                ext:allowDelete "true";
              }
              leaf txInterval {
                type uint32 {
                  range "3..1000";
                }
                description
                  "Specify the minimum interval at which BFD packets are sent. By default, the value is determined by the PAF file.";
                ext:allowDelete "true";
              }
              leaf isSingleHop {
                type boolean;
                must "not(../isBfdEnable='false') or (../isBfdEnable='false' and ../isSingleHop='false')";
                default "false";
                description
                  "The single hop mode is preferred during the BFD session establishment between IBGP peers.";
              }
            }
          }
        }
        container bgpPeers {
          description
            "List of BGP peers.";
          list bgpPeer {
            key "peerAddr";
            description
              "Configurations of a single BGP peer.";
            leaf peerAddr {
              type inet:ip-address-no-zone;
              description
                "Connection address of a peer, which can be an IPv4 or IPv6 address.";
            }
            leaf groupName {
              type leafref {
                path "/bgp/bgpcomm/bgpVrfs/bgpVrf/bgpPeerGroups/bgpPeerGroup/groupName";
              }
              description
                "Specify the name of a peer group that BGP peers need to join. The value is a string, spaces not supported. By default, BGP peers join no peer group. BGP peers distinguish the peer group type when joining a peer group. IBGP peers cannot join an EBGP peer group.  BGP peers will be deleted when they leave a peer group. ";
              ext:allowDelete "true";
            }
            leaf remoteAs {
              type string {
                length "1..11";
              }
              description
                "AS number of a peer, which can be in either two-byte format or four-byte format:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf description {
              type string {
                length "1..255";
                pattern '([^?]*)';
              }
              description
                "Description of a peer, which can be letters or digits. The description is a string of 1 to 80 characters, with spaces supported. By default, no description is configured for a peer.";
              ext:allowDelete "true";
            }
            leaf fakeAs {
              type asNumberValidate {
                length "1..11";
                pattern '((([1-9]\d{0,8})|([1-3]\d{9})|(4[0-1]\d{8})|(42[0-8]\d{7})|(429[0-3]\d{6})|(4294[0-8]\d{5})|(42949[0-5]\d{4})|(429496[0-6]\d{3})|(4294967[0-1]\d{2})|(42949672[0-8]\d{1})|(429496729[0-5]))|((([1-9]\d{0,3})|([1-5]\d{4})|(6[0-4]\d{3})|(65[0-4]\d{2})|(655[0-2]\d)|(6553[0-5]))[\.](([0-9]\d{0,3})|([1-5]\d{4})|(6[0-4]\d{3})|(65[0-4]\d{2})|(655[0-2]\d)|(6553[0-5]))))';
              }
              description
                "Fake AS number that is specified for a local peer. By default, a peer uses the actual AS number of the local end.
An AS number can be in either two-byte format or four-byte format:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf dualAs {
              when "not(../fakeAs)";
              type boolean;
              default "false";
              description
                "By default, dual AS is not enabled, and the remote EBGP peer uses the fake AS number when specifying the AS number for a local peer. 
After dual AS is enabled, the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
            }
            leaf conventional {
              type boolean;
              default "false";
              description
                "Enable general router functions on peers. In conventional mode, not all the extended router functions, such as, route refreshing, GR, and multi-address family negotiation, are available. Therefore, the router of a new version can be compatible with the routers of earlier versions.";
            }
            leaf routeRefresh {
              type boolean;
              default "true";
              description
                "Enable BGP to advertise Refresh messages to peers. By default, this function is enabled.";
            }
            leaf fourByteAs {
              type boolean;
              default "true";
              description
                "Enables BGP to advertise routes carrying 4-byte AS numbers to peers. By default, the function is enabled. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte.  If the 4-byte AS number function is disabled in such a situation, BGP sessions may fail to be established, and route transmission may be affected.";
            }
            leaf isIgnore {
              type boolean;
              default "false";
              description
                "Tear down sessions between peers and clear all related routing information. By default, this function is disabled.";
            }
            leaf localIfName {
              type leafref {
                path "/ifm:ifm/ifm:interfaces/ifm:interface/ifm:ifName";
              }
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
              ext:allowDelete "true";
            }
            leaf localIfAddress {
              type inet:ip-address-no-zone;
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
            }
            leaf ebgpMaxHop {
              type uint32 {
                range "1..255";
              }
              must "not(../validTtlHops>=1 and ../validTtlHops<=255) or (../validTtlHops>=1 and ../validTtlHops<=255 and ../ebgpMaxHop=1)";
              description
                "Maximum number of hops in an indirect EBGP connection. By default, EBGP connections can be established only between directly connected peers. The function must be configured on both ends.";
              ext:allowDelete "true";
            }
            leaf validTtlHops {
              type uint16 {
                range "1..255";
              }
              must "not(../ebgpMaxHop and ../ebgpMaxHop>1 and ../ebgpMaxHop<=255)";
              description
                "";
              ext:allowDelete "true";
            }
            leaf connectMode {
              type bgpcommPeerConnectMode;
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
              ext:allowDelete "true";
            }
            leaf isLogChange {
              type boolean;
              default "true";
              description
                "Enable BGP to record the session status and events of the specified peer or peer group. By default, the function is enabled.";
            }
            leaf pswdType {
              type bgpcommPasswordType;
              must "not(../keyChainName)";
              default "null";
              description
                "Enable BGP peers to establish a TCP connection and perform the Message Digest 5 (MD5) authentication for BGP messages. Plaintexts and ciphertexts are supported.";
              ext:allowDelete "true";
            }
            leaf pswdCipherText {
              when "not(not(../pswdType))";
              type pub-type:passwordExtend {
                length "1..432";
              }
              description
                "Enable BGP peers to establish a TCP connection and perform the Message Digest 5 (MD5) authentication for BGP messages. The character string in a password identifies the contents of the password, spaces not supported. The TCP connection can be established only when the same MD5 authentication password is set on both ends. If a plaintext is used, the maximum password length is 255. If a ciphertext is used, the maximum password length is 392. If the length is set to 0, no password is set.";
              ext:allowDelete "true";
            }
            leaf keepAliveTime {
              type uint32 {
                range "0..21845";
              }
              default "60";
              description
                "Specify the Keepalive time of a peer or peer group. The value is an integer, in seconds. If the value of a timer changes, the peers need to re-negotiate the interval value for the keepalive-time and hold-time. This disconnects the BGP peer relationship between the routers. Therefore, you need to double check whether it is a must to change the value of the timer. Ensure that the hold time is at least three times longer than the keepalive time when you configure the BGP timer.";
              ext:allowDelete "true";
            }
            leaf holdTime {
              type uint32 {
                range "0..65535";
              }
              must "(../holdTime!=1) or (../holdTime!=2) or (../holdTime>=../keepAliveTime*3) or (../holdTime>=../minHoldTime)";
              default "180";
              description
                "Specify the Hold time of a peer or peer group. The value is either 0 or an integer ranging from 0 to 65535, in seconds. When setting the timer values of keepalive-time and hold-time, avoid the following settings: 1.The interval values of keepalive-time and hold-time are both set to 0. This will cause BGP timer to become invalid, and BGP will not detect link faults based on the timer. 
2. The interval value of hold-time is much greater than that of keepalive-time. For example, the interval value of keepalive-time is 1, and that of hold-time is 65535. If the interval value of hold-time is too large, BGP will not be able to detect link faults in time. The priority of the timer configured here is lower than that of timer configured with interval values of keepalive-time and hold-time of a peer. After a connection is established between peers, the interval values of keepalive-time and hold-time are negotiated by the peers. The smaller interval value of hold-time contained in Open packets of both peers is taken as the interval value of hold-time. The smaller interval value of one third of the interval value of hold-time and the locally set interval value of keepalive-time is taken as the interval value of keepalive-time.";
              ext:allowDelete "true";
            }
            leaf minHoldTime {
              type uint32 {
                range "0..65535";
              }
              default "0";
              description
                "The minimum hold time is either 0 or an integer ranging from 20 to 65535, in seconds. If the value is changed, the new value takes effect since the next peer relationship establishment. During the peer relationship establishment, the local device checks the hold time of the remote end. If the hold time is less than the minimum hold time, the local device sends an error packet with error code 02 and subcode 06, and the peer relationship fails to be established.

";
              ext:allowDelete "true";
            }
            leaf keyChainName {
              type string {
                length "1..47";
              }
              must "not(not(../pswdType))";
              description
                "Specify the Keychain authentication name used when BGP peers establish a TCP connection. The value is a string, spaces not supported. By default, the Keychain authentication is not configured. Keychain authentication mode and password authentication mode are mutually exclusive. Configuring Keychain authentication can enhance the security of the TCP connections between BGP peers. Keychain authentication using the same encryption algorithm and password must be configured on the two ends of BGP peers to establish a TCP connection and exchange BGP packets. Before configuring BGP Keychain authentication, you need to configure Keychain according to keychain name. Otherwise, the TCP connections between the BGP peers cannot be established.";
              ext:allowDelete "true";
            }
            leaf connRetryTime {
              type uint16 {
                range "1..65535";
              }
              default "32";
              description
                "ConnectRetry interval. The value is an integer, in seconds. The default value is 32s.";
              ext:allowDelete "true";
            }
            leaf tcpMSS {
              type uint16 {
                range "176..4096";
              }
              description
                "Maximum TCP MSS value used for TCP connection establishment for a peer. ";
              ext:allowDelete "true";
            }
            leaf prependGlobalAs {
              when "not(not(../fakeAs))";
              type boolean;
              default "false";
              description
                "Add the global AS number to the Update packets to be advertised.";
            }
            leaf prependFakeAs {
              when "not(not(../fakeAs))";
              type boolean;
              default "false";
              description
                "Add the Fake AS number to received Update packets.";
            }
            container peerLogInfos {
              config false;
              description
                "Peer log information list.";
              list peerLogInfo {
                key "logIndex";
                config false;
                description
                  "Peer log information. After the log function is enabled on a peer, you can check the recorded log information about the peer.";
                leaf logIndex {
                  type uint32;
                  config false;
                  description
                    "Index of peer log information.";
                }
                leaf stateEvent {
                  type string {
                    length "0..20";
                  }
                  config false;
                  description
                    "Status of a peer when an event occurs.";
                }
                leaf errorCode {
                  type uint8 {
                    range "0..255";
                  }
                  config false;
                  description
                    "Error code that triggers an event.";
                }
                leaf errorSubCode {
                  type uint8 {
                    range "0..255";
                  }
                  config false;
                  description
                    "Error subcode that triggers an event.";
                }
                leaf notification {
                  type string {
                    length "0..40";
                  }
                  config false;
                  description
                    "Sent or received notification messages.";
                }
                leaf logDateTime {
                  type yang:date-and-time;
                  config false;
                  description
                    "Time when the log information was recorded.";
                }
              }
            }
            container peerBfd {
              description
                "Configure BFD.";
              leaf isBfdBlock {
                type boolean;
                default "false";
                description
                  "Prevent  a BGP peer from inheriting the BFD configuration of the BGP peer group.";
              }
              leaf multiplier {
                type uint32 {
                  range "3..50";
                }
                default "3";
                description
                  "Specify the detection multiplier. The default value is 3.";
                ext:allowDelete "true";
              }
              leaf isBfdEnable {
                type boolean;
                default "false";
                description
                  "Enable BFD.";
              }
              leaf rxInterval {
                type uint32 {
                  range "3..1000";
                }
                description
                  "Specify the minimum interval at which BFD packets are received. By default, the value is determined by the PAF file.";
                ext:allowDelete "true";
              }
              leaf txInterval {
                type uint32 {
                  range "3..1000";
                }
                description
                  "Specify the minimum interval at which BFD packets are sent. By default, the value is determined by the PAF file.";
                ext:allowDelete "true";
              }
              leaf isSingleHop {
                type boolean;
                must "not(../isBfdEnable='false') or (../isBfdEnable='false' and ../isSingleHop='false')";
                default "false";
                description
                  "The single hop mode is preferred during the BFD session establishment between IBGP peers.";
              }
            }
          }
        }
        container bgpVrfAFs {
          description
            "List of BGP address family instances.";
          list bgpVrfAF {
            key "afType";
            description
              "BGP address family instance.";
            leaf afType {
              type bgpcommPrefixType;
              description
                "Address family type of a BGP instance. ";
            }
            leaf vrfAsNum {
              when "not(../../../vrfName='_public_')";
              type asNumberValidate {
                length "1..11";
                pattern '((([1-9]\d{0,8})|([1-3]\d{9})|(4[0-1]\d{8})|(42[0-8]\d{7})|(429[0-3]\d{6})|(4294[0-8]\d{5})|(42949[0-5]\d{4})|(429496[0-6]\d{3})|(4294967[0-1]\d{2})|(42949672[0-8]\d{1})|(429496729[0-5]))|((([1-9]\d{0,3})|([1-5]\d{4})|(6[0-4]\d{3})|(65[0-4]\d{2})|(655[0-2]\d)|(6553[0-5]))[\.](([0-9]\d{0,3})|([1-5]\d{4})|(6[0-4]\d{3})|(65[0-4]\d{2})|(655[0-2]\d)|(6553[0-5]))))';
              }
              description
                "Specify the unique AS number for the vpn instance";
              ext:allowDelete "true";
            }
            leaf maxLoadIbgpNum {
              when "not(../afType='evpn' or ../afType='ipv4flow' or ../afType='ipv4vpn' or ../afType='ipv4vpnmcast' or ../afType='ipv6vpn' or ../afType='l2vpnad' or ../afType='ls' or ../afType='mdt' or ../afType='mvpn' and ../../../vrfName!='_public_' or ../afType='mvpn') or ../afType='ipv4uni' or ../afType='ipv6uni'";
              type uint16 {
                range "1..65535";
              }
              default "1";
              description
                "Specify the maximum number of equal-cost IBGP routes. By default, the value is 1. ";
              ext:allowDelete "true";
            }
            leaf ibgpEcmpNexthopChanged {
              when "not(../../../vrfName='_public_' and ../afType='l2vpnad' or ../afType='evpn' or ../afType='ipv4flow' or ../afType='ipv4vpn' or ../afType='ipv4vpnmcast' or ../afType='ipv6vpn' or ../afType='l2vpnad' or ../afType='ls' or ../afType='mdt' or ../afType='mvpn' and ../../../vrfName!='_public_' or ../afType='mvpn') or ../afType='ipv4uni' or ../afType='ipv6uni'";
              type boolean;
              must "../maxLoadIbgpNum and ../maxLoadIbgpNum>1 or (not(../maxLoadIbgpNum and ../maxLoadIbgpNum>1) and ../ibgpEcmpNexthopChanged='false')";
              default "false";
              description
                "When equal-cost IBGP routes are load-balancing traffic, the next hop of these routes is changed to a local interface before these routes are advertised. By default, this function is not enabled. This function can be enabled only when the maximum number of equal-cost IBGP routes is greater than 1.";
            }
            leaf maxLoadEbgpNum {
              when "not(../afType='evpn' or ../afType='ipv4flow' or ../afType='ipv4vpn' or ../afType='ipv4vpnmcast' or ../afType='ipv6vpn' or ../afType='l2vpnad' or ../afType='ls' or ../afType='mdt' or ../afType='mvpn' and ../../../vrfName!='_public_' or ../afType='mvpn') or ../afType='ipv4uni' or ../afType='ipv6uni'";
              type uint16 {
                range "1..65535";
              }
              default "1";
              description
                "Specify the maximum number of equal-cost EBGP routes. By default, the value is 1.";
              ext:allowDelete "true";
            }
            leaf ebgpEcmpNexthopChanged {
              when "not(../../../vrfName='_public_' and ../afType='l2vpnad' or ../afType='evpn' or ../afType='ipv4flow' or ../afType='ipv4vpn' or ../afType='ipv4vpnmcast' or ../afType='ipv6vpn' or ../afType='l2vpnad' or ../afType='ls' or ../afType='mdt' or ../afType='mvpn' and ../../../vrfName!='_public_' or ../afType='mvpn') or ../afType='ipv4uni' or ../afType='ipv6uni'";
              type boolean;
              must "../maxLoadEbgpNum and ../maxLoadEbgpNum>1 or (not(../maxLoadEbgpNum and ../maxLoadEbgpNum>1) and ../ebgpEcmpNexthopChanged='false')";
              default "false";
              description
                "When equal-cost EBGP routes are load-balancing traffic, the next hop of these routes is changed to a local interface before these routes are advertised. By default, this function is not enabled. This function can be enabled only when the maximum number of equal-cost EBGP routes is greater than 1.";
            }
            leaf maximumLoadBalance {
              when "not(../afType!='ipv4uni' and ../afType!='ipv4multi' and ../afType!='ipv6uni' or ../afType='ipv4flow' or ../afType='ipv4vpnmcast' or ../afType='ls' or ../afType='mdt' or ../afType='mvpn' and ../../../vrfName!='_public_')";
              type uint16 {
                range "1..65535";
              }
              default "1";
              description
                "Specify the maximum number of equal-cost routes in the BGP routing table. The value can be 1 or an integer greater than 1. The value depends on the associated license. By default, the maximum number of equal-cost routes is 1. Equal-cost BGP routes can be generated for load balancing only when the BGP routes meet the first nine rules of the route-selection policy and have the same AS-Path attribute.";
              ext:allowDelete "true";
            }
            leaf ecmpNexthopChanged {
              when "not(../../../vrfName='_public_' and ../afType='l2vpnad' or ../afType='evpn' or ../afType='ipv4flow' or ../afType='ipv4vpn' or ../afType='ipv4vpnmcast' or ../afType='ipv6vpn' or ../afType='l2vpnad' or ../afType='ls' or ../afType='mdt' or ../afType='mvpn' and ../../../vrfName!='_public_' or ../afType='mvpn') or ../afType='ipv4uni' or ../afType='ipv6uni'";
              type boolean;
              must "../maximumLoadBalance and ../maximumLoadBalance>1 or (not(../maximumLoadBalance and ../maximumLoadBalance>1) and ../ecmpNexthopChanged='false')";
              default "false";
              description
                "When equal-cost BGP routes are load-balancing traffic, the next hop of these routes is changed to a local interface before these routes are advertised. By default, this function is not enabled. This function can be enabled only when the maximum number of equal-cost BGP routes is greater than 1.";
            }
            leaf eibgpLoadBalan {
              when "not(../afType='ipv4vpnmcast' or ../afType='ls' or ../afType='mdt' or ../afType='mvpn' and ../../../vrfName!='_public_') or ../../../vrfName!='_public_'";
              type uint16 {
                range "1..65535";
              }
              description
                "Specify the maximum number of equal-cost EBGP routes and IBGP routes. After the attribute is set, load balancing is performed among equal-cost BGP VPN routes, regardless of the route type, EBGP or IBGP. By default, the maximum number of equal-cost EBGP routes and IBGP routes is 0.";
              ext:allowDelete "true";
            }
            leaf eibgpEcmpNexthopChanged {
              when "not(../afType='ls' or ../afType='mvpn' and ../../../vrfName!='_public_') or ../../../vrfName!='_public_'";
              type boolean;
              must "../eibgpLoadBalan and ../eibgpLoadBalan>0 or (not(../eibgpLoadBalan and ../eibgpLoadBalan>0) and ../eibgpEcmpNexthopChanged='false')";
              default "false";
              description
                "When equal-cost EBGP and IBGP routes are load-balancing traffic, the next hop of these routes is changed to a local interface before these routes are advertised. By default, this function is not enabled. ";
            }
            leaf defaultLocalPref {
              when "not(../afType='evpn' or ../afType='ipv4flow' or ../afType='ipv4vpnmcast' or ../afType='ls' or ../afType='mdt' or ../afType='mvpn' and ../../../vrfName!='_public_' or ../afType='mvpn')";
              type uint32 {
                range "0..4294967295";
              }
              default "100";
              description
                "Set the Local-Preference attribute. The value is an integer. The greater the value, the higher the priority. By default, the Local-Preference for BGP is 100. Setting different Local-Preferences affects BGP route selection. When a router that runs BGP has multiple routes to the same destination, the router selects the route with the highest Local-Preference. The Local-Preference is exchanged only between IBGP peers and is not advertised to other ASs.";
              ext:allowDelete "true";
            }
            leaf defaultMed {
              when "not(../afType='evpn' or ../afType='ipv4flow' or ../afType='ipv4vpnmcast' or ../afType='l2vpnad' or ../afType='ls' or ../afType='mdt' or ../afType='mvpn' and ../../../vrfName!='_public_' or ../afType='mvpn')";
              type uint32 {
                range "0..4294967295";
              }
              description
                "Specify the Multi-Exit-Discriminator (MED) of BGP routes. The value is an integer. By default, the MED is 0. This value is valid only for the imported routes and BGP summarized routes on the local router.
";
              ext:allowDelete "true";
            }
            leaf defaultRtImportEnable {
              when "not(../afType='ipv4vpnmcast' or ../afType='ls' or ../afType='mdt' or ../afType='mvpn' and ../../../vrfName!='_public_') or ../afType!='ipv6vpn' and ../afType!='ipv4vpn' and ../afType!='ipv4flow' and ../afType!='mvpn' and ../afType!='l2vpnad' and ../afType!='evpn' and ../afType!='ipv4vpnmcast' and ../afType!='mdt' and ../afType!='ls'";
              type boolean;
              default "false";
              description
                "Import default routes into the BGP routing table. By default, BGP does not add default routes to the BGP routing table. default-route-imported must be used with import-routes so that default routes can be imported to the BGP routing table. If only import-routes is used, no default routes can be added to the BGP routing table. In addition, default-route-imported can only import the default routes in the routing table into the BGP routing table.";
            }
            leaf routerId {
              when "not(../afType='ipv4vpnmcast' or ../afType='ls' or ../afType='mdt' or ../afType='mvpn' and ../../../vrfName!='_public_') or ../../../vrfName!='_public_'";
              type inet:ipv4-address-no-zone;
              must "../vrfRidAutoSel!='true'";
              description
                "ID of a router that is in IPv4 address format. Certain dynamic routing protocols require a router ID. If no router ID is specified for a router when these protocols are enabled, the router ID in the RM module is used by default. The default router ID in the RM module is 0.0.0.0 when the router is not configured with any interface. 
The rules for selecting a router ID are as follows:
1. If you set a router ID through this configuration, the set router ID is used. If the router ID is not set, you need to select a router ID according to the following rules:
(1) If loopback interfaces configured with IP addresses exist, the largest IP address among the IP addresses of the loopback interfaces is selected as the router ID.
(2) If no loopback interface configured with an IP address exists, the largest IP address among the IP addresses of other interfaces is selected as the router ID, regardless of whether the interface is Up.
The router ID is reselected only when the interface address that is selected as the router ID is deleted or changed. The router ID is not reselected in any of the following cases:
a. The interface is Down.
b. A loopback interface is configured when the IP address of a non-loopback interface is selected as the router ID.
c. A larger IP address of an interface is configured.
2. Each VPN instance selects the router ID from the addresses of the interfaces of the VPN instance according to the preceding rules.
3. When both the AMB and SMB exist on the router, the system backs up the router ID set through the related command and the router ID that is selected from IP addresses of the interfaces. After the active/standby switchover is performed, the system checks the validity of the router ID selected from the interface addresses. If the router ID is invalid, the system reselects a router ID.";
              ext:allowDelete "true";
            }
            leaf vrfRidAutoSel {
              when "not(../afType='ipv4vpnmcast' or ../afType='ls' or ../afType='mdt' or ../afType='mvpn' and ../../../vrfName!='_public_') or ../../../vrfName!='_public_'";
              type boolean;
              must "not(../routerId)";
              description
                "By default, a BGP VPN instance does not automatically select a router ID. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
1. If Loopback interfaces configured with IP addresses exist, the largest IP address among the IP addresses of the Loopback interfaces is selected as the router ID. 
2. If there is no Loopback interface configured with an IP address, the largest IP address among the IP addresses of other interfaces is selected as the router ID, regardless of whether the interface is Up.";
            }
            leaf nexthopThirdParty {
              when "not(../afType='ipv4vpnmcast' or ../afType='mdt') or ../afType='ipv4uni'";
              type boolean;
              default "false";
              description
                "Enable BGP third-party next hop.";
            }
            leaf summaryAutomatic {
              when "not(../afType!='ipv4uni' and ../afType!='ipv4multi' or ../afType='ipv4vpnmcast' or ../afType='ls' or ../afType='mdt' or ../afType='mvpn' and ../../../vrfName!='_public_')";
              type boolean;
              default "false";
              description
                "Enable automatic summarization for imported routes. By default, the locally imported routes are not summarized automatically. Manual summarization takes precedence over automatic summarization. After automatic summarization is enabled, BGP summarizes routes based on the natural network segment (for example, 10.1.1.1/24 and 10.2.1.1/24 are summarized into 10.0.0.0/8, a Class A address), and sends only the summarized route to peers. This reduces the number of routes.";
            }
            leaf autoFrrEnable {
              when "not(../afType='ipv4vpnmcast' or ../afType='ls' or ../afType='mdt' or ../afType='mvpn' and ../../../vrfName!='_public_') or ../afType!='ipv4multi' and ../afType!='ipv4flow' and ../afType!='ipv6vpn' and ../afType!='l2vpnad' and ../afType!='mvpn' and ../afType!='evpn' and ../afType!='ipv4vpnmcast' and ../afType!='mdt' and ../afType!='ls'";
              type boolean;
              default "false";
              description
                "Enable BGP Auto FRR. By default, BGP Auto FRR is disabled. If IP FRR, VPN FRR, and Auto FRR are all enabled, IP FRR and VPN FRR take precedence over Auto FRR. If a route fails to match the routing policy of IP FRR or VPN FRR, Auto FRR takes effect.";
            }
            leaf bwBcNonstd {
              when "../afType='ls'";
              type boolean;
              default "false";
              description
                "BGP-LS advertise and parse Bandwidth BC";
            }
            leaf loadBalancingAsPathIgnore {
              when "not(../afType='ls' or ../afType='mvpn' and ../../../vrfName!='_public_' or ../asPathNeglect='true') or ../afType!='ipv6vpn' and ../afType!='ipv4vpn' and ../afType!='ipv4flow' and ../afType!='mvpn' and ../afType!='l2vpnad' and ../afType!='evpn' and ../afType!='ipv4vpnmcast' and ../afType!='mdt' and ../afType!='ls' or ../asPathNeglect!='true' and ../afType!='ipv6vpn' and ../afType!='ipv4vpn' and ../afType!='ipv4flow' and ../afType!='mvpn' and ../afType!='l2vpnad' and ../afType!='evpn' and ../afType!='mdt' and ../afType!='ls'";
              type boolean;
              default "false";
              description
                "Configure BGP to ignore the AS_Path of each BGP route to the next hop when selecting routes for load balancing. By default, only the routes with the same AS_Path can participate in load balancing.";
            }
            leaf multiHomingNonStdEnable {
              type boolean;
              default "false";
              description
                "Enable capability of multi-homing for Virtual Private LAN Services ";
            }
            leaf medPlusIgp {
              when "../afType!='ipv4flow' and ../afType!='mdt' and ../afType!='l2vpnad' and ../afType!='mvpn' and ../afType!='evpn' and ../afType!='ipv4vpnmcast' and ../afType!='ls' and ../igpMetricIgnore='false'";
              type boolean;
              default "false";
              description
                "add the IGP cost to the next-hop destination to the MED before comparing MED values for path selection.";
            }
            leaf medMultiplier {
              when "../medPlusIgp='true'";
              type uint16 {
                range "1..1000";
              }
              default "1";
              description
                "Value of med product factor";
              ext:allowDelete "true";
            }
            leaf igpMultiplier {
              when "../medPlusIgp='true'";
              type uint16 {
                range "1..1000";
              }
              default "1";
              description
                "Value of igp cost product factor";
              ext:allowDelete "true";
            }
            leaf ribOnlyEnable {
              when "not(../../../vrfName!='_public_' or ../../../vrfName='_public_' and ../afType!='ipv4uni' and ../afType!='ipv6uni' and ../afType!='ipv4flow' or ../afType='ipv4vpnmcast' or ../afType='mdt')";
              type boolean;
              must "not(../activeRouteAdvertise='true')";
              default "false";
              description
                "Prevent BGP routes from being added to the IP routing table. By default, preferred BGP routes are added to the IP routing table.";
            }
            leaf ribOnlyPolicyName {
              when "not(../../../vrfName!='_public_' or ../../../vrfName='_public_' and ../afType!='ipv4multi' and ../afType!='ipv4vpn' and ../afType!='ipv6vpn' and ../afType!='ipv4flow' and ../afType!='l2vpnad' and ../afType!='mvpn' and ../afType!='evpn' and ../afType!='mdt' and ../afType!='ls' and ../ribOnlyEnable='true' and ../ribOnlyRtFilterName or ../../../vrfName='_public_' and ../afType!='ipv4multi' and ../afType!='ipv4vpn' and ../afType!='ipv6vpn' and ../afType!='l2vpnad' and ../afType!='mvpn' and ../afType!='evpn' and ../afType!='ls' and ../ribOnlyEnable='false' or ../../../vrfName='_public_' and ../afType!='ipv4uni' and ../afType!='ipv6uni' and ../afType!='ipv4flow' or ../afType='ipv4vpnmcast' or ../afType='mdt') or ../../../vrfName='_public_' and ../afType!='ipv4multi' and ../afType!='ipv4vpn' and ../afType!='ipv6vpn' and ../afType!='l2vpnad' and ../afType!='mvpn' and ../afType!='evpn' and ../afType!='mdt' and ../afType!='ls' and ../ribOnlyEnable='true'";
              type policyName {
                length "1..200";
                pattern '([^\? ]+)';
              }
              description
                "Specify the name of a routing policy. When both rib-only-enable and rib-only-policy-name are used, the routes that match the routing policy are not added to the IP routing table. Conversely, the routes that do not match the routing policy are added to the IP routing table, and the attributes of these routes are not modified.";
              ext:allowDelete "true";
            }
            leaf activeRouteAdvertise {
              when "not(../afType='ipv4vpnmcast' or ../afType='ls' or ../afType='mdt' or ../afType='mvpn' and ../../../vrfName!='_public_') or ../afType!='ipv4multi' and ../afType!='ipv4vpn' and ../afType!='ipv6vpn' and ../afType!='ipv4flow' and ../afType!='l2vpnad' and ../afType!='mvpn' and ../afType!='evpn' and ../afType!='ls'";
              type boolean;
              must "not(../ribOnlyEnable='true')";
              default "false";
              description
                "Advertise the optimal routes in the RM module to peers.";
            }
            leaf asPathNeglect {
              when "not(../afType='ipv4vpnmcast' or ../afType='ls' or ../afType='mdt' or ../afType='mvpn' and ../../../vrfName!='_public_' or ../loadBalancingAsPathIgnore='true') or ../afType!='ipv6vpn' and ../afType!='ipv4vpn' and ../afType!='ipv4flow' and ../afType!='mvpn' and ../afType!='l2vpnad' and ../afType!='evpn' and ../afType!='ipv4vpnmcast' and ../afType!='mdt' and ../afType!='ls' or ../loadBalancingAsPathIgnore!='true' and ../afType!='ipv6vpn' and ../afType!='ipv4vpn' and ../afType!='ipv4flow' and ../afType!='mvpn' and ../afType!='l2vpnad' and ../afType!='evpn' and ../afType!='mdt' and ../afType!='ls'";
              type boolean;
              default "false";
              description
                "Configure BGP to ignore the AS_Path attribute when selecting the optimal route. By default, BGP uses the AS_Path attribute as one of route selection rules, and a route with a shorter AS_Path is preferred. After as-path-neglect is selected, BGP does not compare the AS_Path length.";
            }
            leaf medNoneAsMaximum {
              when "not(../afType='ipv4vpnmcast' or ../afType='ls' or ../afType='mdt' or ../afType='mvpn' and ../../../vrfName!='_public_') or ../afType!='ipv6vpn' and ../afType!='ipv4vpn' and ../afType!='ipv4flow' and ../afType!='mvpn' and ../afType!='l2vpnad' and ../afType!='evpn' and ../afType!='ipv4vpnmcast' and ../afType!='mdt' and ../afType!='ls'";
              type boolean;
              default "false";
              description
                "If a route does not carry MED, BGP considers its MED as the default value (0) during route selection. After med-none-as-maximum is selected, BGP considers its MED as the largest MED value (4294967295).";
            }
            leaf routerIdNeglect {
              when "../afType!='ipv6vpn' and ../afType!='ipv4vpn' and ../afType!='ipv4flow' and ../afType!='mvpn' and ../afType!='l2vpnad' and ../afType!='evpn' and ../afType!='ipv4vpnmcast' and ../afType!='mdt' and ../afType!='ls'";
              type boolean;
              default "false";
              description
                "Configure BGP to ignore router IDs when selecting the optimal route. Comparing router IDs is the last resort in route selection. This means that if one optimal route must be selected and no other parameters can be used to break the tie, router IDs can be used. If this option is selected, the first received route will be selected as the optimal route, and BGP will ignore the router ID and peer address in route selection.";
            }
            leaf igpMetricIgnore {
              when "not(../afType='ls' or ../afType='mvpn' and ../../../vrfName!='_public_') or ../afType!='ipv4flow' and ../afType!='mdt' and ../afType!='l2vpnad' and ../afType!='mvpn' and ../afType!='evpn' and ../afType!='ipv4vpnmcast' and ../afType!='ls' and ../medPlusIgp='false'";
              type boolean;
              default "false";
              description
                "Configure BGP to ignore the IGP cost of each BGP route to the next hop in route selection. By default, a BGP route with a smaller IGP cost to the next hop is preferred.";
            }
            leaf alwaysCompareMed {
              when "not(../afType='ipv4vpnmcast' or ../afType='ls' or ../afType='mdt' or ../afType='mvpn' and ../../../vrfName!='_public_') or ../afType!='ipv6vpn' and ../afType!='ipv4vpn' and ../afType!='ipv4flow' and ../afType!='mvpn' and ../afType!='l2vpnad' and ../afType!='evpn' and ../afType!='ipv4vpnmcast' and ../afType!='mdt' and ../afType!='ls'";
              type boolean;
              default "false";
              description
                "Configure BGP to compare the MEDs of routes from peers in different ASs in route selection. By default, BGP does not compare the MEDs of routes from peers in different ASs. If there are multiple reachable routes to the same destination, the route with the smallest MED is preferred. Do not use this option unless different ASs use the same IGP and route selection mode.";
            }
            leaf determinMed {
              when "not(../afType='ipv4vpnmcast' or ../afType='ls' or ../afType='mdt' or ../afType='mvpn' and ../../../vrfName!='_public_') or ../afType!='ipv6vpn' and ../afType!='ipv4vpn' and ../afType!='ipv4flow' and ../afType!='mvpn' and ../afType!='l2vpnad' and ../afType!='evpn' and ../afType!='ipv4vpnmcast' and ../afType!='mdt' and ../afType!='ls'";
              type boolean;
              must "../bestExternal!='true' and not(../addPathSelNum)";
              default "false";
              description
                "Enable deterministic MED so that the route selection result is relevant to the sequence in which routes are received.";
            }
            leaf preferenceExternal {
              when "not(../afType!='ipv4uni' and ../afType!='ipv4multi' and ../afType!='ipv6uni' or ../afType='ipv4vpnmcast' or ../afType='mdt') or ../afType!='ipv6vpn' and ../afType!='ipv4vpn' and ../afType!='ipv4flow' and ../afType!='mvpn' and ../afType!='l2vpnad' and ../afType!='evpn' and ../afType!='ipv4vpnmcast' and ../afType!='mdt' and ../afType!='ls' and not(../prefrencePolicyName) and not(../prefRtFilterName)";
              type uint8 {
                range "1..255";
              }
              default "255";
              description
                "Set the protocol priority of EBGP routes. The value is an integer. An EBGP route is the optimal route learned from a peer outside the local AS.";
              ext:allowDelete "true";
            }
            leaf preferenceInternal {
              when "not(../afType!='ipv4uni' and ../afType!='ipv4multi' and ../afType!='ipv6uni' or ../afType='ipv4vpnmcast' or ../afType='mdt') or ../afType!='ipv6vpn' and ../afType!='ipv4vpn' and ../afType!='ipv4flow' and ../afType!='mvpn' and ../afType!='l2vpnad' and ../afType!='evpn' and ../afType!='ipv4vpnmcast' and ../afType!='mdt' and ../afType!='ls' and not(../prefrencePolicyName) and not(../prefRtFilterName)";
              type uint8 {
                range "1..255";
              }
              default "255";
              description
                "Set the protocol priority of IBGP routes. The value is an integer. An IBGP route is a route learned from a peer inside the local AS.";
              ext:allowDelete "true";
            }
            leaf preferenceLocal {
              when "not(../afType!='ipv4uni' and ../afType!='ipv4multi' and ../afType!='ipv6uni' or ../afType='ipv4vpnmcast' or ../afType='mdt') or ../afType!='ipv6vpn' and ../afType!='ipv4vpn' and ../afType!='ipv4flow' and ../afType!='mvpn' and ../afType!='l2vpnad' and ../afType!='evpn' and ../afType!='ipv4vpnmcast' and ../afType!='mdt' and ../afType!='ls' and not(../prefrencePolicyName) and not(../prefRtFilterName)";
              type uint8 {
                range "1..255";
              }
              default "255";
              description
                "Set the protocol priority of a local BGP route. The value is an integer. A local route refers to an automatically or manually summarized route.";
              ext:allowDelete "true";
            }
            leaf prefrencePolicyName {
              when "not(../afType!='ipv4uni' and ../afType!='ipv4multi' and ../afType!='ipv6uni' or ../afType!='ipv6vpn' and ../afType!='ipv4vpn' and ../afType!='ipv4flow' and ../afType!='mvpn' and ../afType!='l2vpnad' and ../afType!='evpn' and ../afType!='ipv4vpnmcast' and ../afType!='mdt' and ../afType!='ls' and ../prefRtFilterName or ../afType='ipv4vpnmcast' or ../afType='mdt') or ../afType!='ipv6vpn' and ../afType!='ipv4vpn' and ../afType!='ipv4flow' and ../afType!='mvpn' and ../afType!='l2vpnad' and ../afType!='evpn' and ../afType!='ipv4vpnmcast' and ../afType!='mdt' and ../afType!='ls' and ../preferenceExternal=255 and ../preferenceInternal=255 and ../preferenceLocal=255 and not(../prefRtFilterName)";
              type policyName {
                length "1..200";
                pattern '([^\? ]+)';
              }
              description
                "Set a routing policy to filter routes so that a configured priority is applied to the routes that match the specified policy. The routes that do not meet the policy rules use the default priority.";
              ext:allowDelete "true";
            }
            leaf reflectBetweenClient {
              when "not(../afType='mvpn' and ../../../vrfName!='_public_') or ../afType='ls'";
              type boolean;
              default "true";
              description
                "Enable route reflection between clients. By default, route reflection is enabled between clients. If clients of a route reflector (RR) are fully meshed, you can disable route reflection among clients to reduce the cost.";
            }
            leaf reflectorClusterId {
              when "not(../afType='mvpn' and ../../../vrfName!='_public_') or ../afType='ls'";
              type uint32 {
                range "1..4294967295";
              }
              description
                "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
              ext:allowDelete "true";
            }
            leaf reflectorClusterIpv4 {
              when "not(../afType='mvpn' and ../../../vrfName!='_public_') or ../afType='ls'";
              type inet:ipv4-address-no-zone;
              description
                "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
              ext:allowDelete "true";
            }
            leaf rrFilterNumber {
              when "not(../../../vrfName!='_public_' or ../afType!='ipv4vpn' and ../afType!='ipv6vpn' and ../afType!='l2vpnad' and ../afType!='mvpn' and ../../../vrfName='_public_' and ../afType!='mdt' or ../afType='ipv4vpnmcast' or ../afType='ls' or ../afType='mvpn' and ../../../vrfName!='_public_')";
              type leafref {
                path "/rtp:rtp/rtp:extendCommunityFilters/rtp:extendCommunityFilter/rtp:index";
              }
              description
                "Set the number of the extended community filter supported by an RR group. For the purpose of load balancing, only the IBGP route whose route-target extended community attribute meets the matching rules can be reflected. The name of an extended community filter can be a numeral or a character string. The ID of an extended community filter is an integer ranging from 1 to 399. The name of an extended community filter is a string of 1 to 51 characters. The string cannot contain only numerals.";
              ext:allowDelete "true";
            }
            leaf policyVpnTarget {
              when "not(../../../vrfName!='_public_' and ../afType='ipv4uni' or ../../../vrfName!='_public_' and ../afType='ipv6uni' or ../../../vrfName!='_public_' or ../afType!='ipv4vpn' and ../afType!='ipv6vpn' and ../afType!='l2vpnad' and ../afType!='mvpn' and ../../../vrfName='_public_' and ../afType!='mdt' and ../afType!='evpn' or ../afType='ls' or ../afType='mvpn' and ../../../vrfName!='_public_') or ../../../vrfName='_public_' and ../afType='ipv4vpnmcast' or ../../../vrfName='_public_' and ../afType='mdt'";
              type boolean;
              default "true";
              description
                "Enable VPN target-based filtering for the received VPN routes. By default, VPN target-based filtering is enabled. Only the VPN route whose Export RT attribute matches the local Import RT attribute can be added to the routing table.  This option can be used in the inter-AS VPN Option B solution and the ASBR MP-EBGP inter-AS L2VPN solution in Kompella mode.";
            }
            leaf nhpRelayRoutePolicyName {
              when "not(../afType!='ipv4flow' and ../afType!='l2vpnad' and ../afType!='mvpn' and ../afType!='evpn' and ../afType!='ipv4vpnmcast' and ../afType!='mdt' and ../afType!='ls' and ../nhpRelayRouteFilterName or ../afType='evpn' or ../afType='ipv4flow' or ../afType='ipv4vpnmcast' or ../afType='l2vpnad' or ../afType='ls' or ../afType='mdt' or ../afType='mvpn' and ../../../vrfName!='_public_' or ../afType='mvpn') or ../afType!='ipv4flow' and ../afType!='l2vpnad' and ../afType!='mvpn' and ../afType!='evpn' and ../afType!='ipv4vpnmcast' and ../afType!='mdt' and ../afType!='ls' and not(../nhpRelayRouteFilterName)";
              type policyName {
                length "1..200";
                pattern '([^\? ]+)';
              }
              description
                "Specify the name of a route-policy for route iteration.";
              ext:allowDelete "true";
            }
            leaf ebgpIfSensitive {
              when "not(../afType!='ipv4uni' and ../afType!='ipv6uni' or ../afType='ipv4vpnmcast' or ../afType='ls' or ../afType='mdt' or ../afType='mvpn' and ../../../vrfName!='_public_')";
              type boolean;
              default "true";
              description
                "After the function of EBGP interface fast sensing is enabled, the sessions of directly connected EBGP peers are immediately cleared from the associated interface when the interface becomes Down. By default, this function is enabled.";
            }
            leaf reflectChgPath {
              when "not(../afType='evpn' or ../afType='ipv4flow' or ../afType='ls' or ../afType='mvpn' and ../../../vrfName!='_public_')";
              type boolean;
              default "false";
              description
                "Enable an RR to use an export policy to change route AS_Path. By default, this function is not enabled.";
            }
            leaf slowPeerDet {
              when "not(../afType='ipv4flow')";
              type boolean;
              default "true";
              description
                "Detect slow peers";
            }
            leaf slowPeerThVal {
              when "not(../afType='ipv4flow')";
              type uint16 {
                range "120..3600";
              }
              description
                "Specify the time in seconds lagging behind average when a peer is determined to be a slow peer, default is 300";
              ext:allowDelete "true";
            }
            leaf slowPeerAbDet {
              type boolean;
              default "false";
              description
                "Enable absolute-detect slow peers.";
            }
            leaf slowPeerAbThVal {
              type uint16 {
                range "3..3600";
              }
              description
                "Specify the packet send delay time in second when a peer is determined to be a slow peer, default is 9";
              ext:allowDelete "true";
            }
            leaf routeSelDelay {
              when "not(../afType='evpn' or ../afType='ipv4flow' or ../afType='ipv4vpnmcast' or ../afType='ls' or ../afType='mvpn' and ../../../vrfName!='_public_') or ../afType!='mvpn' and ../afType!='evpn' and ../afType!='ipv4flow' and ../afType!='ls' or ../afType='mvpn' and ../../../vrfName='_public_'";
              type uint16 {
                range "0..3600";
              }
              default "0";
              description
                "Route selection delay. ";
              ext:allowDelete "true";
            }
            leaf originAsValidEnable {
              when "not(../afType='ipv4vpnmcast' or ../afType='ls' or ../afType='mdt' or ../afType='mvpn' and ../../../vrfName!='_public_') or ../afType!='ipv4multi' and ../afType!='ipv4vpn' and ../afType!='ipv6vpn' and ../afType!='ipv4flow' and ../afType!='l2vpnad' and ../afType!='mvpn' and ../afType!='evpn' and ../afType!='ipv4vpnmcast' and ../afType!='mdt' and ../afType!='ls'";
              type boolean;
              default "false";
              description
                "Enable BGP origin AS validation.";
            }
            leaf originAsValid {
              when "not(../afType='ipv4vpnmcast' or ../afType='ls' or ../afType='mdt' or ../afType='mvpn' and ../../../vrfName!='_public_') or ../afType!='ipv4multi' and ../afType!='ipv4vpn' and ../afType!='ipv6vpn' and ../afType!='ipv4flow' and ../afType!='l2vpnad' and ../afType!='mvpn' and ../afType!='evpn' and ../afType!='ipv4vpnmcast' and ../afType!='mdt' and ../afType!='ls' or ../originAsValidEnable='true'";
              type boolean;
              default "false";
              description
                "Apply the BGP origin AS validation result to route selection.";
            }
            leaf allowInvalidAs {
              when "not(../afType='ipv4vpnmcast' or ../afType='ls' or ../afType='mdt' or ../afType='mvpn' and ../../../vrfName!='_public_') or ../afType!='ipv4multi' and ../afType!='ipv4vpn' and ../afType!='ipv6vpn' and ../afType!='ipv4flow' and ../afType!='l2vpnad' and ../afType!='mvpn' and ../afType!='evpn' and ../afType!='ipv4vpnmcast' and ../afType!='mdt' and ../afType!='ls' or ../originAsValid='true'";
              type boolean;
              default "false";
              description
                "Allow routes with BGP origin AS validation result Invalid to be selected.";
            }
            leaf policyExtCommEnable {
              when "not(../afType='ipv4vpnmcast' or ../afType='ls' or ../afType='mdt' or ../afType='mvpn' and ../../../vrfName!='_public_') or ../afType!='ipv6vpn' and ../afType!='ipv4vpn' and ../afType!='ipv4flow' and ../afType!='mvpn' and ../afType!='l2vpnad' and ../afType!='evpn' and ../afType!='ipv4vpnmcast' and ../afType!='mdt' and ../afType!='ls'";
              type boolean;
              default "false";
              description
                "Change the extended community attribute.";
            }
            leaf policyQPPBEnable {
              when "not(../afType='ipv4vpnmcast' or ../afType='ls' or ../afType='mdt' or ../afType='mvpn' and ../../../vrfName!='_public_') or ../../../vrfName='_public_' and ../afType='ipv6uni'";
              type boolean;
              default "false";
              description
                "Enable QPPB.";
            }
            leaf supernetUniAdv {
              when "not(../afType='evpn' or ../afType='ipv4vpnmcast' or ../afType='ls' or ../afType='mdt' or ../afType='mvpn' and ../../../vrfName!='_public_' or ../afType='mvpn') or ../afType!='ipv4multi' and ../afType!='ipv4vpn' and ../afType!='ipv6vpn' and ../afType!='ipv4flow' and ../afType!='l2vpnad' and ../afType!='ls'";
              type boolean;
              default "false";
              description
                "Advertise supernet unicast routes.";
            }
            leaf originatorPrior {
              when "not(../afType='ipv4vpnmcast' or ../afType='ls' or ../afType='mdt' or ../afType='mvpn' and ../../../vrfName!='_public_') or ../afType!='ipv4flow' and ../afType!='mvpn' and ../afType!='evpn' and ../afType!='ipv4vpnmcast' and ../afType!='mdt' and ../afType!='ls'";
              type boolean;
              default "false";
              description
                "Configure BGP to compare originator before clusterlist in route selection.";
            }
            leaf lowestPriority {
              when "not(../afType='ipv4vpnmcast' or ../afType='mdt') or ../../../vrfName='_public_' and ../afType!='ipv4multi' and ../afType!='ipv4vpn' and ../afType!='ipv6vpn' and ../afType!='ipv4vpnmcast' and ../afType!='mdt' and ../afType!='ls' and ../afType!='evpn'";
              type boolean;
              default "false";
              description
                "Reduce route priority to lowest.";
            }
            leaf relayDelayEnable {
              when "not(../afType!='ipv4uni' and ../afType!='ipv6uni' and ../afType!='ipv4vpn' and ../afType!='ipv6vpn')";
              type boolean;
              default "true";
              description
                "Enable relay delay processing.";
              ext:allowDelete "true";
            }
            leaf vrfImportnhpinvariable {
              when "not(../afType='ipv4vpnmcast' or ../afType='mdt' or ../afType='mvpn' and ../../../vrfName!='_public_') or ../../../vrfName!='_public_'";
              type boolean;
              default "false";
              description
                "Configure the command to enable advertise the route without modifying the next-hop.";
            }
            container vrfAFBriefInfo {
              config false;
              description
                "Address family information.";
              leaf peerNum {
                type uint32;
                config false;
                description
                  "Set the number of peers in a specified address family.";
              }
              leaf routeNum {
                type uint32;
                config false;
                description
                  "Set the number of routes in a specified address family.";
              }
            }
            container peerGroupAFs {
              description
                "List of all peer groups that are enabled in a specified address family.";
              list peerGroupAF {
                when "not(../../afType='ipv4flow' or ../../afType='mvpn' and ../../../../vrfName!='_public_')";
                key "groupName groupType";
                description
                  "Peer group enabled in a specified address family.";
                leaf groupName {
                  type leafref {
                    path "/bgp/bgpcomm/bgpVrfs/bgpVrf/bgpPeerGroups/bgpPeerGroup/groupName";
                  }
                  description
                    "Configure a name for a peer group. The value is a string, spaces not supported.";
                }
                leaf groupType {
                  type bgpcommPeerType;
                  description
                    "Configure a peer group type: IBGP or EBGP. The type must be consistent with the peer group type.";
                }
                leaf advertiseCommunity {
                  when "../../../afType!='evpn' and ../../../afType!='ls' or ../../../afType='ipv4vpnmcast'";
                  type boolean;
                  default "false";
                  description
                    "Advertise the community attribute to a peer or a peer group. By default, the community attribute is not advertised to any peer.";
                }
                leaf advertiseExtCommunity {
                  when "not(../../../afType='evpn' or ../../../afType='ipv4vpnmcast' or ../../../afType='mdt' or ../../../afType='mvpn') or ../../../afType!='ipv6vpn' and ../../../afType!='ipv4vpn' and ../../../afType!='l2vpnad' and ../../../afType!='evpn' and ../../../afType!='ipv4vpnmcast' and ../../../afType!='ls'";
                  type boolean;
                  default "false";
                  description
                    "Advertise the extended community attribute to a peer or a peer group. By default, the extended community attribute is not advertised to any peer.";
                }
                leaf discardExtCommunity {
                  when "not(../../../afType='ipv4vpnmcast' or ../../../afType='mdt') or ../../../afType!='ipv4vpn' and ../../../afType!='ipv6vpn' and ../../../afType!='l2vpnad' and ../../../afType!='mvpn' and ../../../afType!='evpn' and ../../../afType!='ipv4vpnmcast' and ../../../afType!='mdt' and ../../../afType!='ls' or ../../../afType!='ipv6vpn' and ../../../afType!='ipv4vpn' and ../../../afType!='l2vpnad' and ../../../afType!='evpn' and ../../../afType!='ipv4vpnmcast' and ../../../afType!='ls'";
                  type boolean;
                  default "false";
                  description
                    "Discard the extended community attribute in the routes learned from a specified peer. By default, the extended community attribute is not discarded. ";
                }
                leaf allowAsLoopEnable {
                  when "not(../../../afType='ipv4vpnmcast' or ../../../afType='mdt' or ../../../afType='mvpn') or ../../../afType!='ipv4flow' and ../../../afType!='mvpn' and ../../../afType!='ipv4vpnmcast' and ../../../afType!='mdt' and ../../../afType!='ls' and ../../../afType!='evpn'";
                  type boolean;
                  mandatory true;
                  description
                    "Allow the repetitive local AS numbers. By default, local AS numbers cannot be repeated.";
                }
                leaf allowAsLoopLimit {
                  when "not(../../../afType='ipv4vpnmcast' or ../../../afType='mdt') or ../../../afType!='ipv4flow' and ../../../afType!='mvpn' and ../../../afType!='ipv4vpnmcast' and ../../../afType!='mdt' and ../../../afType!='ls' and ../../../afType!='evpn' or ../allowAsLoopEnable='true'";
                  type uint32 {
                    range "1..10";
                  }
                  description
                    "Configure the number of allowed AS number repetition times. The value is an integer. The default value is 1.";
                  ext:allowDelete "true";
                }
                leaf keepAllRoutes {
                  when "not(../../../afType='evpn' or ../../../afType='ipv4vpnmcast' or ../../../afType='mdt' or ../../../afType='mvpn') or ../../../afType!='ipv4flow' and ../../../afType!='l2vpnad' and ../../../afType!='mvpn' and ../../../afType!='evpn' and ../../../afType!='ipv4vpnmcast' and ../../../afType!='mdt' and ../../../afType!='ls'";
                  type boolean;
                  default "false";
                  description
                    "Save all the updated information about BGP routes from a specified peer or peer group after a BGP connection is established, even though these BGP routes fail to match the routing policy on the ingress. By default, the updated information about BGP routes from a specified peer is saved only when the routes match the routing policy on the ingress. If a router supports route refreshing, this option is not required.";
                }
                leaf nextHopConfigure {
                  when "not(../../../afType!='ipv4uni' and ../../../afType!='ipv6uni' and ../../../afType!='ipv4vpn' and ../../../afType!='ipv6vpn' and ../../../afType!='evpn' and ../../../afType!='l2vpnad' and ../../../afType!='mvpn' and ../../../afType!='mdt' and ../../../afType!='ipv4multi' or ../../../afType='ipv4vpnmcast')";
                  type bgpcommNextHopCfg;
                  must "(../../../afType!='ipv4uni' and ../../../afType!='ipv4vpn' and ../../../afType!='ipv6vpn' and ../../../afType!='l2vpnad' and ../../../afType!='evpn' and (../nextHopConfigure='null' or ../nextHopConfigure='local') ) or ((not(../../../afType!='ipv4uni' and ../../../afType!='ipv4vpn' and ../../../afType!='ipv6vpn' and ../../../afType!='l2vpnad' and ../../../afType!='evpn') and (../nextHopConfigure='null' or ../nextHopConfigure='local' or ../nextHopConfigure='invariable') ))";
                  default "null";
                  description
                    "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address. ";
                  ext:allowDelete "true";
                }
                leaf preferredValue {
                  when "not(../../../afType='evpn' or ../../../afType='ipv4vpnmcast' or ../../../afType='mdt' or ../../../afType='mvpn') or ../../../afType!='ipv6vpn' and ../../../afType!='ipv4vpnmcast' and ../../../afType!='mdt' and ../../../afType!='ls'";
                  type uint32 {
                    range "0..65535";
                  }
                  default "0";
                  description
                    "Assign a preferred value for the routes learned from a specified peer. The value is an integer. By default, the preferred value of the route learnt from BGP peers is 0. After a preferred value is configured for the routes learned from a specified peer, all the routes that learnt from this peer will use this preferred value. When multiple routes reach the same address prefix, the route with the largest preferred value will be selected.";
                  ext:allowDelete "true";
                }
                leaf publicAsOnly {
                  when "not(../../../afType='ipv4vpnmcast' or ../../../afType='mdt') or ../../../afType!='ipv4flow' and ../../../afType!='mvpn' and ../../../afType!='ipv4vpnmcast' and ../../../afType!='mdt' and ../../../afType!='ls' and ../../../afType!='evpn'";
                  type boolean;
                  default "false";
                  description
                    "Configure BGP to send Update packets carrying only public AS numbers. By default, private AS numbers can be carried in BGP Update packets.";
                }
                leaf publicAsOnlyForce {
                  when "../publicAsOnly='true' and ../publicAsOnlyLimited='false'";
                  type boolean;
                  must "(../../../afType!='mvpn' and ../../../afType!='ipv4flow' and ../../../afType!='evpn' and ../publicAsOnly='false' and ../../../afType!='ipv4vpnmcast' and ../../../afType!='mdt' and ../../../afType!='ls' and ../publicAsOnlyForce='false') and (not(../../../afType!='mvpn' and ../../../afType!='ipv4flow' and ../../../afType!='evpn' and ../publicAsOnly='false' and ../../../afType!='ipv4vpnmcast' and ../../../afType!='mdt' and ../../../afType!='ls')) or (../publicAsOnlyLimited='true' and ../publicAsOnlyForce='false') or not(../../../afType!='mvpn' and ../../../afType!='ipv4flow' and ../../../afType!='evpn' and ../publicAsOnly='false' and ../../../afType!='ipv4vpnmcast' and ../../../afType!='mdt' and ../../../afType!='ls' or ../publicAsOnlyLimited='true')";
                  default "false";
                  description
                    "Configures BGP to carry only the public AS number instead of the private AS number when BGP sends Update packets. By default, BGP can carry the private AS number when BGP sends Update packets.";
                  ext:allowDelete "true";
                }
                leaf publicAsOnlyLimited {
                  when "../publicAsOnly='true' and ../publicAsOnlyForce='false'";
                  type boolean;
                  must "(../../../afType!='mvpn' and ../../../afType!='ipv4flow' and ../../../afType!='evpn' and ../publicAsOnly='false' and ../../../afType!='ipv4vpnmcast' and ../../../afType!='mdt' and ../../../afType!='ls' and ../publicAsOnlyLimited='false') and (not(../../../afType!='mvpn' and ../../../afType!='ipv4flow' and ../../../afType!='evpn' and ../publicAsOnly='false' and ../../../afType!='ipv4vpnmcast' and ../../../afType!='mdt' and ../../../afType!='ls')) or (../publicAsOnlyForce='true' and ../publicAsOnlyLimited='false') or not(../../../afType!='mvpn' and ../../../afType!='ipv4flow' and ../../../afType!='evpn' and ../publicAsOnly='false' and ../../../afType!='ipv4vpnmcast' and ../../../afType!='mdt' and ../../../afType!='ls' or ../publicAsOnly='true' and ../publicAsOnlyForce='false' or ../publicAsOnlyForce='true')";
                  default "false";
                  description
                    "When the BGP sends update packets, the left ends of both the local AS and public AS do not carry the private AS. By default, BGP can carry the private AS number when BGP sends Update packets.";
                  ext:allowDelete "true";
                }
                leaf publicAsOnlyReplace {
                  when "../../../afType!='mvpn' and ../../../afType!='ipv4flow' and ../../../afType!='evpn' and ../publicAsOnly='true' and ../../../afType!='ipv4vpnmcast' and ../../../afType!='mdt' and ../../../afType!='ls'";
                  type boolean;
                  must "not(../../../afType!='mvpn' and ../../../afType!='ipv4flow' and ../../../afType!='evpn' and ../publicAsOnly='false' and ../../../afType!='ipv4vpnmcast' and ../../../afType!='mdt' and ../../../afType!='ls') or (../../../afType!='mvpn' and ../../../afType!='ipv4flow' and ../../../afType!='evpn' and ../publicAsOnly='false' and ../../../afType!='ipv4vpnmcast' and ../../../afType!='mdt' and ../../../afType!='ls' and ../publicAsOnlyReplace='false') and (not(../../../afType!='mvpn' and ../../../afType!='ipv4flow' and ../../../afType!='evpn' and ../publicAsOnly='false' and ../../../afType!='ipv4vpnmcast' and ../../../afType!='mdt' and ../../../afType!='ls'))";
                  default "false";
                  description
                    "When the BGP sends update packets, the private AS is replaced by the local AS. By default, BGP can carry the private AS number when BGP sends Update packets.";
                  ext:allowDelete "true";
                }
                leaf publicAsOnlySkipPeerAs {
                  when "../../../afType!='mvpn' and ../../../afType!='ipv4flow' and ../../../afType!='evpn' and ../publicAsOnly='true' and ../../../afType!='ipv4vpnmcast' and ../../../afType!='mdt' and ../../../afType!='ls'";
                  type boolean;
                  must "not(../../../afType!='mvpn' and ../../../afType!='ipv4flow' and ../../../afType!='evpn' and ../publicAsOnly='false' and ../../../afType!='ipv4vpnmcast' and ../../../afType!='mdt' and ../../../afType!='ls') or (../../../afType!='mvpn' and ../../../afType!='ipv4flow' and ../../../afType!='evpn' and ../publicAsOnly='false' and ../../../afType!='ipv4vpnmcast' and ../../../afType!='mdt' and ../../../afType!='ls' and ../publicAsOnlySkipPeerAs='false') and (not(../../../afType!='mvpn' and ../../../afType!='ipv4flow' and ../../../afType!='evpn' and ../publicAsOnly='false' and ../../../afType!='ipv4vpnmcast' and ../../../afType!='mdt' and ../../../afType!='ls'))";
                  default "false";
                  description
                    "When the BGP sends update packets, the neigbour AS is not processed. By default, BGP can carry the private AS number when BGP sends Update packets.";
                  ext:allowDelete "true";
                }
                leaf routeLimit {
                  type uint32 {
                    range "1..4294967295";
                  }
                  mandatory true;
                  description
                    "Configure the maximum number of routes that can be accepted from a peer. ";
                  ext:allowDelete "true";
                }
                leaf routeLimitPercent {
                  when "../routeLimit";
                  type uint8 {
                    range "1..100";
                  }
                  default "75";
                  description
                    "Specify the percentage of routes when a router starts to generate an alarm. The default value is 75.";
                  ext:allowDelete "true";
                }
                leaf routeLimitType {
                  when "../routeLimit";
                  type bgpcommRouteLmtType;
                  default "noparameter";
                  description
                    "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
                  ext:allowDelete "true";
                }
                leaf routeLimitIdleTimeout {
                  when "../routeLimitType='idleTimeout'";
                  type uint16 {
                    range "1..1200";
                  }
                  default "1";
                  description
                    "Specify the value of the idle-timeout timer to automatically reestablish the connections after they are cut off when the number of routes exceeds the set threshold.";
                  ext:allowDelete "true";
                }
                leaf rtUpdtInterval {
                  when "not(../../../afType='ipv4vpnmcast') or ../../../afType!='ipv6vpn' and ../../../afType!='ipv4vpn' and ../../../afType!='l2vpnad' and ../../../afType!='evpn' and ../../../afType!='ipv4vpnmcast'";
                  type uint16 {
                    range "0..600";
                  }
                  description
                    "Specify the minimum interval at which Update packets are sent. The value is an integer, in seconds. By default, the interval at which Update packets are sent to IBGP peers is 15s, and the interval at which Update packets are sent to EBGP peers is 30s. When routes change, a router will send Update packets to notify its peers. If a route changes frequently, you can set an interval at which Update packets are sent to prevent the router from sending Update packets each time the route changes. This configuration is valid only to the routes learned from peers. ";
                  ext:allowDelete "true";
                }
                leaf reflectClient {
                  when "not(../groupType='ebgp')";
                  type boolean;
                  must "not(../advBestExternal='true')";
                  default "false";
                  description
                    "Configure the local device as a route reflector (RR) and a peer or peer group as its client. By default, the RR and its client are not configured. This configuration is applicable between IBGP peers only. The configurations of RRs and its clients in an address family are valid only in this address family. Therefore, it is recommended to configure RRs and its clients in the specified address family that is required.";
                }
                leaf substituteAsEnable {
                  when "../../../afType!='ipv4multi' and ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls'";
                  type boolean;
                  default "false";
                  description
                    "Replace the AS number of a specified peer in the AS_Path attribute with the local AS number. By default, the AS number replacement is disabled. On a PE where AS number replacement is enabled, if an AS number in the AS_Path attribute of a route is same as that of the CE to which the PE advertises the route, the PE replaces the AS number with its own AS number before advertising the route.";
                }
                leaf importRtPolicyName {
                  when "not(../importRtFilterName) or ../../../afType='ipv4vpnmcast'";
                  type leafref {
                    path "/rtp:rtp/rtp:routePolicys/rtp:routePolicy/rtp:name";
                  }
                  description
                    "Specify the filtering policy applied to the routes learned from a peer. By default, no such policy is specified.";
                  ext:allowDelete "true";
                }
                leaf exportRtPolicyName {
                  when "not(../exportRtFilterName) or ../../../afType='ipv4vpnmcast'";
                  type leafref {
                    path "/rtp:rtp/rtp:routePolicys/rtp:routePolicy/rtp:name";
                  }
                  description
                    "Specify the filtering policy applied to the routes to be advertised to a peer. By default, no such policy is specified.";
                  ext:allowDelete "true";
                }
                leaf importPrefFiltName {
                  when "not(../../../afType!='ipv4uni' and ../../../afType!='ipv4multi' and ../../../afType!='ipv4vpn' and ../../../afType!='mdt' or ../../../afType='evpn' or ../../../afType='ipv4vpnmcast' or ../../../afType='mvpn') or ../../../afType='mdt'";
                  type ipPrefix {
                    length "1..169";
                    pattern '([^\? ]+)';
                  }
                  description
                    "Specify the IPv4 filtering policy applied to the routes received from a specified peer. By default, no such policy is specified.";
                  ext:allowDelete "true";
                }
                leaf importPref6FiltName {
                  when "not(../../../afType!='ipv6uni' and ../../../afType!='ipv6vpn' or ../../../afType='ipv4vpnmcast' or ../../../afType='mdt')";
                  type ipPrefix {
                    length "1..169";
                    pattern '([^\? ]+)';
                  }
                  description
                    "Specify the IPv6 filtering policy applied to the routes received from a specified peer. By default, no such policy is specified.";
                  ext:allowDelete "true";
                }
                leaf exportPrefFiltName {
                  when "not(../../../afType!='ipv4uni' and ../../../afType!='ipv4multi' and ../../../afType!='ipv4vpn' and ../../../afType!='mdt' or ../../../afType='evpn' or ../../../afType='ipv4vpnmcast' or ../../../afType='mdt' or ../../../afType='mvpn')";
                  type ipPrefix {
                    length "1..169";
                    pattern '([^\? ]+)';
                  }
                  description
                    "Specify the IPv4 filtering policy applied to the routes to be advertised to a specified peer. By default, no such policy is specified.";
                  ext:allowDelete "true";
                }
                leaf exportPref6FiltName {
                  when "not(../../../afType!='ipv6uni' and ../../../afType!='ipv6vpn' or ../../../afType='ipv4vpnmcast' or ../../../afType='mdt')";
                  type ipPrefix {
                    length "1..169";
                    pattern '([^\? ]+)';
                  }
                  description
                    "Specify the IPv6 filtering policy applied to the routes to be advertised to a specified peer. By default, no such policy is specified.";
                  ext:allowDelete "true";
                }
                leaf importAsPathNameOrNum {
                  when "not(../../../afType='ipv4vpnmcast' or ../../../afType='mdt') or ../../../afType!='ipv4flow' and ../../../afType!='l2vpnad' and ../../../afType!='evpn' and ../../../afType!='ipv4vpnmcast' and ../../../afType!='ls'";
                  type leafref {
                    path "/rtp:rtp/rtp:asPathFilters/rtp:asPathFilter/rtp:index";
                  }
                  description
                    "Apply an AS_Path-based filtering policy to the routes received from a specified peer. The policy can be identified with a name or number, and the number ranges from 1 to 256. By default, no such policy is specified. Therefore, all BGP routes can be accepted.";
                  ext:allowDelete "true";
                }
                leaf exportAsPathNameOrNum {
                  when "not(../../../afType='ipv4vpnmcast' or ../../../afType='mdt') or ../../../afType!='ipv4flow' and ../../../afType!='l2vpnad' and ../../../afType!='evpn' and ../../../afType!='ipv4vpnmcast' and ../../../afType!='ls'";
                  type leafref {
                    path "/rtp:rtp/rtp:asPathFilters/rtp:asPathFilter/rtp:index";
                  }
                  description
                    "Apply an AS_Path-based filtering policy to the routes to be advertised to a specified peer. The policy can be identified with a name or number, and the number ranges from 1 to 256. By default, no such policy is specified. Therefore, all BGP routes can be advertised.";
                  ext:allowDelete "true";
                }
                leaf importAclNameOrNum {
                  when "not(../../../afType!='ipv4uni' and ../../../afType!='ipv4multi' and ../../../afType!='ipv4vpn' and ../../../afType!='mdt' or ../../../afType='ipv4vpnmcast') or ../../../afType='mdt'";
                  type leafref {
                    path "/acl:acl/acl:aclGroups/acl:aclGroup/acl:aclNumOrName";
                  }
                  description
                    "Apply an IPv4 ACL-based filtering policy to the routes received from a specified peer. The ACL number ranges from 2000 to 2999, and the name must start with a letter. By default, no such policy is specified. Therefore, all BGP routes can be accepted.";
                  ext:allowDelete "true";
                }
                leaf importAcl6NameOrNum {
                  when "not(../../../afType!='ipv6uni' and ../../../afType!='ipv6vpn' or ../../../afType='ipv4vpnmcast' or ../../../afType='mdt')";
                  type acl6NumOrName {
                    length "1..32";
                    pattern '(^2[0-9]{3}$)|(^[a-zA-Z]([^\s]*$))';
                  }
                  description
                    "Apply an IPv6 ACL-based filtering policy to the routes received from a specified peer. The ACL number ranges from 2000 to 2999, and the name must start with a letter. By default, no such policy is specified. Therefore, all BGP routes can be accepted.";
                  ext:allowDelete "true";
                }
                leaf exportAclNameOrNum {
                  when "not(../../../afType!='ipv4uni' and ../../../afType!='ipv4multi' and ../../../afType!='ipv4vpn' and ../../../afType!='mdt' or ../../../afType='ipv4vpnmcast' or ../../../afType='mdt')";
                  type leafref {
                    path "/acl:acl/acl:aclGroups/acl:aclGroup/acl:aclNumOrName";
                  }
                  description
                    "Apply an IPv4 ACL-based filtering policy to the routes to be advertised to a specified peer. The ACL number ranges from 2000 to 2999, and the name must start with a letter. By default, no such policy is specified. Therefore, all BGP routes can be advertised.";
                  ext:allowDelete "true";
                }
                leaf exportAcl6NameOrNum {
                  when "not(../../../afType!='ipv6uni' and ../../../afType!='ipv6vpn' or ../../../afType='ipv4vpnmcast' or ../../../afType='mdt')";
                  type acl6NumOrName {
                    length "1..32";
                    pattern '(^2[0-9]{3}$)|(^[a-zA-Z]([^\s]*$))';
                  }
                  description
                    "Apply an IPv6 ACL-based filtering policy to the routes to be advertised to a specified peer. The ACL number ranges from 2000 to 2999, and the name must start with a letter. By default, no such policy is specified. Therefore, all BGP routes can be advertised.";
                  ext:allowDelete "true";
                }
                leaf ipprefixOrfEnable {
                  when "not(../../../afType='ipv4vpnmcast' or ../../../afType='mdt') or ../../../afType='ipv4uni'";
                  type boolean;
                  must "not(../isNonstdIpprefixMod='true')";
                  default "false";
                  description
                    "Enable Prefix-based BGP outbound route filtering (ORF). By default, this function is not enabled. ORF enables a BGP device to use the import policy of a peer as the local export policy so that unwanted routes are filtered out during route advertisement.";
                  ext:allowDelete "true";
                }
                leaf isNonstdIpprefixMod {
                  when "not(../../../afType='ipv4vpnmcast' or ../../../afType='mdt') or ../../../afType='ipv4uni'";
                  type boolean;
                  must "not(../ipprefixOrfEnable='true')";
                  default "false";
                  description
                    "Enable Huawei routers to be compatible with Nonstandard routers. The ORF capability codes supported by Nonstandard devices are different from that defined by the associated RFC standard. After the option is selected, Huawei devices and Nonstandard devices negotiate ORF capability based on the ORF capability code supported by Nonstandard devices. If the option is not selected, Huawei devices and Nonstandard devices negotiate ORF capability based on the ORF capability code specified by the RFC standard.";
                  ext:allowDelete "true";
                }
                leaf orftype {
                  when "not(../../../afType='ipv4vpnmcast' or ../../../afType='mdt') or ../../../afType='ipv4uni'";
                  type uint16;
                  description
                    "ORF Type.";
                  ext:allowDelete "true";
                }
                leaf orfMode {
                  when "not(../../../afType='ipv4vpnmcast' or ../../../afType='mdt') or ../../../afType='ipv4uni'";
                  type bgpcommonOrfMode;
                  must "(../ipprefixOrfEnable!='true' and ../isNonstdIpprefixMod!='true' and (../orfMode='null') ) or ((not(../ipprefixOrfEnable!='true' and ../isNonstdIpprefixMod!='true') and (../orfMode='receive' or ../orfMode='send' or ../orfMode='both') ))";
                  default "null";
                  description
                    "Configure an outbound route filtering (ORF) mode, which can be Receive, Send, or Both, and the default ORF mode is Both. ";
                  ext:allowDelete "true";
                }
                leaf soostring {
                  when "not(../../../afType='ipv4vpnmcast' or ../../../afType='mdt') or ../../../../../vrfName!='_public_' or ../../../afType!='ipv4multi' and ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls' or ../../../afType!='ipv4multi' and ../../../afType!='ipv4vpn' and ../../../afType!='ipv6vpn' and ../../../afType!='ipv4flow' and ../../../afType!='l2vpnad' and ../../../afType!='mvpn' and ../../../afType!='evpn' and ../../../afType!='mdt' and ../../../afType!='ls' and ../../../../../vrfName!='_public_' or ../../../afType='ipv4uni' and ../../../../../vrfName!='_public_' or ../../../afType='ipv6uni' and ../../../../../vrfName!='_public_'";
                  type string {
                    length "3..21";
                  }
                  description
                    "Configure the Site-of-Origin (SoO) extended community attribute. This attribute can be expressed in the following formats: X.X.X.X:number<0-65535>, number<0-65535>:number<0-4294967295>, or number<0-65535>.number<0-65535>:number<0-65535>  or <65536-4294967295>:<0-65535>. 0:0 or 0.0:0 is not supported. 
Two CEs are in the same site and can advertise routes to each other, and they are connected to a VPN through PEs. If the local routes of a CE are advertised to the other CE over the VPN, a routing loop may occur. 
The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops. ";
                  ext:allowDelete "true";
                }
                leaf defaultRtAdvEnable {
                  when "not(../../../afType!='ipv4uni' and ../../../afType!='ipv4multi' and ../../../afType!='ipv6uni' or ../../../afType='ipv4vpnmcast' or ../../../afType='mdt')";
                  type boolean;
                  default "false";
                  description
                    "Enable a device to advertise the default route to its peers. By default, the device does not advertise the default route to any peer or peer group. This option enables a device to send a default route with the device as the next hop address to its peers, regardless of whether there is a default route in the local routing table.";
                }
                leaf defaultRtAdvPolicy {
                  when "not(../../../afType!='ipv4uni' and ../../../afType!='ipv4multi' and ../../../afType!='ipv6uni' or ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls' and ../defaultRtAdvEnable='false' or ../../../afType='ipv4vpnmcast' or ../../../afType='mdt') or ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls' and ../defaultRtAdvEnable='true'";
                  type policyName {
                    length "1..200";
                    pattern '([^\? ]+)';
                  }
                  description
                    "Specify the name of a used policy. The value is a string.";
                  ext:allowDelete "true";
                }
                leaf defaultRtMatchMode {
                  when "not(../../../afType='ipv4vpnmcast' or ../../../afType='mdt') or ../../../afType='ipv4uni' and ../defaultRtAdvEnable='true'";
                  type bgpcommonCraMatchMode;
                  default "null";
                  description
                    "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  ext:allowDelete "true";
                }
                leaf labelRouteCapability {
                  when "not(../../../afType='evpn' or ../../../afType='ipv4vpnmcast' or ../../../afType='mdt') or ../../../afType!='ipv4multi' and ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls' or ../../../afType!='ipv4multi' and ../../../afType!='ipv4vpn' and ../../../afType!='ipv6vpn' and ../../../afType!='ipv4flow' and ../../../afType!='l2vpnad' and ../../../afType!='mvpn' and ../../../afType!='evpn' and ../../../afType!='ls' and ../../../afType!='ipv4vpnmcast'";
                  type boolean;
                  default "false";
                  description
                    "Enable a device to exchange labeled routes";
                  ext:allowDelete "true";
                }
                leaf originAsValid {
                  when "not(../../../afType='ipv4vpnmcast' or ../../../afType='mdt') or ../advertiseExtCommunity='true' and ../../../afType!='ipv4multi' and ../../../afType!='ipv4flow' and ../../../afType!='l2vpnad' and ../../../afType!='mvpn' and ../../../afType!='evpn' and ../../../afType!='ipv4vpnmcast' and ../../../afType!='mdt' and ../../../afType!='ls'";
                  type boolean;
                  default "false";
                  description
                    "Advertises the BGP origin AS validation result to the specified BGP peer or peer group.";
                  ext:allowDelete "true";
                }
                leaf updatePktStandardCompatible {
                  when "../../../afType='ipv4vpnmcast'";
                  type boolean;
                  default "false";
                  description
                    "Compatible Standard update packet";
                  ext:allowDelete "true";
                }
                container peerGroupAFCraPres {
                  when "not(../../../afType='ipv4vpnmcast' or ../../../afType='mdt')";
                  must "not(not(../defaultRtMatchMode)) or (not(../defaultRtMatchMode) and count(peerGroupAFCraPre)>=1)";
                  description
                    "Configure the matching conditions for default route advertisement. (Only the default routes that match the conditions can be advertised.)";
                  list peerGroupAFCraPre {
                    when "not(../../defaultRtMatchMode) and ../../../../afType='ipv4uni'";
                    key "defaultRtAddress defaultRtMask";
                    max-elements  "4";
                    description
                      "Configure the matching condition for default route advertisement.";
                    leaf defaultRtAddress {
                      type inet:ipv4-address-no-zone;
                      description
                        "Configure a prefix that is used to match default routes.";
                    }
                    leaf defaultRtMask {
                      type uint32 {
                        range "0..32";
                      }
                      description
                        "Configure a mask that is used to match default routes.";
                    }
                  }
                }
                container peerAFMembers {
                  when "not(../../../afType='ipv4vpnmcast' or ../../../afType='mdt')";
                  config false;
                  description
                    "List of peers in the peer address family.";
                  list peerAFMember {
                    key "peer";
                    config false;
                    description
                      "Peer in the peer address family.";
                    leaf peer {
                      type string {
                        length "1..512";
                      }
                      config false;
                      description
                        "Peer address in the peer address family.";
                    }
                  }
                }
              }
            }
            container peerAFs {
              description
                "Peers in a specified address family.";
              list peerAF {
                when "not(../../afType='mvpn' and ../../../../vrfName!='_public_')";
                key "remoteAddress";
                description
                  "Peer in a specified address family.";
                leaf remoteAddress {
                  type leafref {
                    path "/bgp/bgpcomm/bgpVrfs/bgpVrf/bgpPeers/bgpPeer/peerAddr";
                  }
                  description
                    "IPv4 or IPv6 peer connection address.";
                }
                leaf peerGroupName {
                  when "not(../../../afType='ipv4flow')";
                  type leafref {
                    path "/bgp/bgpcomm/bgpVrfs/bgpVrf/bgpVrfAFs/bgpVrfAF/peerGroupAFs/peerGroupAF/groupName";
                  }
                  description
                    "Configure a name for a peer group. After a peer is deleted from the peer group, the peer is disabled from the address family.";
                  ext:allowDelete "true";
                }
                leaf advertiseCommunity {
                  when "not(../../../afType='evpn') or ../../../afType!='evpn' and ../../../afType!='ipv4vpnmcast' and ../../../afType!='ls' or ../../../afType!='evpn' and ../../../afType!='ls'";
                  type boolean;
                  default "false";
                  description
                    "Advertise the community attribute to a peer or peer group. By default, the community attribute is not advertised to any peer or peer group.";
                  ext:allowDelete "true";
                }
                leaf advertiseExtCommunity {
                  when "not(../../../afType='evpn' or ../../../afType='ipv4vpnmcast' or ../../../afType='mdt' or ../../../afType='mvpn') or ../../../afType!='ipv6vpn' and ../../../afType!='ipv4vpn' and ../../../afType!='ipv4flow' and ../../../afType!='l2vpnad' and ../../../afType!='evpn' and ../../../afType!='mvpn' and ../../../afType!='ipv4vpnmcast' and ../../../afType!='mdt' and ../../../afType!='ls'";
                  type boolean;
                  default "false";
                  description
                    "Advertise the extended community attribute to a peer or peer group. By default, the extended community attribute is not advertised to any peer or peer group.";
                  ext:allowDelete "true";
                }
                leaf discardExtCommunity {
                  when "not(../../../afType='ipv4vpnmcast' or ../../../afType='mdt') or ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls'";
                  type boolean;
                  default "false";
                  description
                    "Discard the extended community attribute in the routing information about a specified peer. By default, the extended community attribute in the routing information about a specified peer is not discarded.";
                  ext:allowDelete "true";
                }
                leaf allowAsLoopEnable {
                  when "not(../../../afType='ipv4flow' or ../../../afType='ipv4vpnmcast' or ../../../afType='mdt' or ../../../afType='mvpn') or ../../../afType!='ipv4flow' and ../../../afType!='mvpn' and ../../../afType!='ipv4vpnmcast' and ../../../afType!='mdt' and ../../../afType!='ls'";
                  type boolean;
                  mandatory true;
                  description
                    "Allow repetitive local AS numbers. By default, repetitive local AS numbers are not allowed.";
                  ext:allowDelete "true";
                }
                leaf allowAsLoopLimit {
                  when "not(../../../afType='ipv4vpnmcast' or ../../../afType='mdt') or ../../../afType!='ipv4flow' and ../../../afType!='mvpn' and ../../../afType!='ipv4vpnmcast' and ../../../afType!='mdt' and ../../../afType!='ls' or ../allowAsLoopEnable='true'";
                  type uint32 {
                    range "1..10";
                  }
                  description
                    "with";
                  ext:allowDelete "true";
                }
                leaf keepAllRoutes {
                  when "not(../../../afType='ipv4vpnmcast' or ../../../afType='mdt') or ../../../afType!='ipv4flow' and ../../../afType!='l2vpnad' and ../../../afType!='mvpn' and ../../../afType!='evpn' and ../../../afType!='ipv4vpnmcast' and ../../../afType!='mdt' and ../../../afType!='ls'";
                  type boolean;
                  default "false";
                  description
                    "Save all the updated information about BGP routes from a specified peer or peer group after a BGP connection is established, even though these BGP routes fail to match the routing policy on the ingress. By default, the updated information about BGP routes from a specified peer is saved only when the routes match the routing policy on the ingress. If a router supports route refreshing, this option is not required.";
                  ext:allowDelete "true";
                }
                leaf nextHopConfigure {
                  when "not(../../../afType!='ipv4uni' and ../../../afType!='ipv6uni' and ../../../afType!='ipv4vpn' and ../../../afType!='ipv6vpn' and ../../../afType!='evpn' and ../../../afType!='l2vpnad' and ../../../afType!='mvpn' and ../../../afType!='mdt' and ../../../afType!='ipv4multi' or ../../../afType='ipv4flow' or ../../../afType='ipv4vpnmcast' or ../../../afType='ls') or ../../../afType='evpn'";
                  type bgpcommNextHopCfg;
                  must "(../../../afType!='ipv4uni' and ../../../afType!='ipv4vpn' and ../../../afType!='ipv6vpn' and ../../../afType!='l2vpnad' and ../../../afType!='evpn' and (../nextHopConfigure='null' or ../nextHopConfigure='local') ) or ((not(../../../afType!='ipv4uni' and ../../../afType!='ipv4vpn' and ../../../afType!='ipv6vpn' and ../../../afType!='l2vpnad' and ../../../afType!='evpn') and (../nextHopConfigure='null' or ../nextHopConfigure='local' or ../nextHopConfigure='invariable') ))";
                  description
                    "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address. ";
                  ext:allowDelete "true";
                }
                leaf preferredValue {
                  when "not(../../../afType='ipv4vpnmcast' or ../../../afType='mdt') or ../../../afType!='ipv4flow' and ../../../afType!='mvpn' and ../../../afType!='evpn' and ../../../afType!='ipv4vpnmcast' and ../../../afType!='mdt' and ../../../afType!='ls'";
                  type uint32 {
                    range "0..65535";
                  }
                  default "0";
                  description
                    "Assign a preferred value for the routes learned from a specified peer. The value is an integer. By default, the preferred value of the route learnt from BGP peers is 0. After a preferred value is configured for the routes learned from a specified peer, all the routes that learnt from this peer will use this preferred value. When multiple routes reach the same address prefix, the route with the largest preferred value will be selected.";
                  ext:allowDelete "true";
                }
                leaf publicAsOnly {
                  when "not(../../../afType='evpn' or ../../../afType='ipv4flow' or ../../../afType='ipv4vpnmcast' or ../../../afType='mdt' or ../../../afType='mvpn') or ../../../afType!='mvpn' and ../../../afType!='ipv4flow' and ../../../afType!='evpn' and ../../../afType!='ipv4vpnmcast' and ../../../afType!='mdt' and ../../../afType!='ls'";
                  type boolean;
                  default "false";
                  description
                    "Configure BGP to send Update packets carrying only public AS numbers. By default, private AS numbers can be carried in BGP Update packets.";
                  ext:allowDelete "true";
                }
                leaf publicAsOnlyForce {
                  when "../publicAsOnly='true' and ../publicAsOnlyLimited='false'";
                  type boolean;
                  must "(../../../afType!='mvpn' and ../../../afType!='ipv4flow' and ../../../afType!='evpn' and ../publicAsOnly='false' and ../../../afType!='ipv4vpnmcast' and ../../../afType!='mdt' and ../../../afType!='ls' and ../publicAsOnlyForce='false') or (../publicAsOnlyLimited='true' and ../publicAsOnlyForce='false') or not(../../../afType!='mvpn' and ../../../afType!='ipv4flow' and ../../../afType!='evpn' and ../publicAsOnly='false' and ../../../afType!='ipv4vpnmcast' and ../../../afType!='mdt' and ../../../afType!='ls' or ../publicAsOnlyLimited='true')";
                  default "false";
                  description
                    "Configures BGP to carry only the public AS number instead of the private AS number when BGP sends Update packets. By default, BGP can carry the private AS number when BGP sends Update packets.";
                  ext:allowDelete "true";
                }
                leaf publicAsOnlyLimited {
                  when "../publicAsOnly='true' and ../publicAsOnlyForce='false'";
                  type boolean;
                  must "(../../../afType!='mvpn' and ../../../afType!='ipv4flow' and ../../../afType!='evpn' and ../publicAsOnly='false' and ../../../afType!='ipv4vpnmcast' and ../../../afType!='mdt' and ../../../afType!='ls' and ../publicAsOnlyLimited='false') or (../publicAsOnlyForce='true' and ../publicAsOnlyLimited='false') or not(../../../afType!='mvpn' and ../../../afType!='ipv4flow' and ../../../afType!='evpn' and ../publicAsOnly='false' and ../../../afType!='ipv4vpnmcast' and ../../../afType!='mdt' and ../../../afType!='ls' or ../publicAsOnlyForce='true')";
                  default "false";
                  description
                    "When the BGP sends update packets, the left ends of both the local AS and public AS do not carry the private AS. By default, BGP can carry the private AS number when BGP sends Update packets.";
                  ext:allowDelete "true";
                }
                leaf publicAsOnlyReplace {
                  when "../../../afType!='mvpn' and ../../../afType!='ipv4flow' and ../../../afType!='evpn' and ../publicAsOnly='true' and ../../../afType!='ipv4vpnmcast' and ../../../afType!='mdt' and ../../../afType!='ls'";
                  type boolean;
                  must "not(../../../afType!='mvpn' and ../../../afType!='ipv4flow' and ../../../afType!='evpn' and ../publicAsOnly='false' and ../../../afType!='ipv4vpnmcast' and ../../../afType!='mdt' and ../../../afType!='ls') or (../../../afType!='mvpn' and ../../../afType!='ipv4flow' and ../../../afType!='evpn' and ../publicAsOnly='false' and ../../../afType!='ipv4vpnmcast' and ../../../afType!='mdt' and ../../../afType!='ls' and ../publicAsOnlyReplace='false')";
                  default "false";
                  description
                    "When the BGP sends update packets, the private AS is replaced by the local AS. By default, BGP can carry the private AS number when BGP sends Update packets.";
                  ext:allowDelete "true";
                }
                leaf publicAsOnlySkipPeerAs {
                  when "../../../afType!='mvpn' and ../../../afType!='ipv4flow' and ../../../afType!='evpn' and ../publicAsOnly='true' and ../../../afType!='ipv4vpnmcast' and ../../../afType!='mdt' and ../../../afType!='ls'";
                  type boolean;
                  must "not(../../../afType!='mvpn' and ../../../afType!='ipv4flow' and ../../../afType!='evpn' and ../publicAsOnly='false' and ../../../afType!='ipv4vpnmcast' and ../../../afType!='mdt' and ../../../afType!='ls') or (../../../afType!='mvpn' and ../../../afType!='ipv4flow' and ../../../afType!='evpn' and ../publicAsOnly='false' and ../../../afType!='ipv4vpnmcast' and ../../../afType!='mdt' and ../../../afType!='ls' and ../publicAsOnlySkipPeerAs='false')";
                  default "false";
                  description
                    "When the BGP sends update packets, the neigbour AS is not processed. By default, BGP can carry the private AS number when BGP sends Update packets.";
                  ext:allowDelete "true";
                }
                leaf routeLimit {
                  type uint32 {
                    range "1..4294967295";
                  }
                  mandatory true;
                  description
                    "Configure the maximum number of routes that can be accepted from a peer. ";
                  ext:allowDelete "true";
                }
                leaf routeLimitPercent {
                  when "../routeLimit";
                  type uint8 {
                    range "1..100";
                  }
                  default "75";
                  description
                    "Specify the percentage of routes when a router starts to generate an alarm. The default value is 75.";
                  ext:allowDelete "true";
                }
                leaf routeLimitType {
                  when "../routeLimit";
                  type bgpcommRouteLmtType;
                  default "noparameter";
                  description
                    "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
                  ext:allowDelete "true";
                }
                leaf routeLimitIdleTimeout {
                  when "../routeLimitType='idleTimeout'";
                  type uint16 {
                    range "1..1200";
                  }
                  default "1";
                  description
                    "Specify the value of the idle-timeout timer to automatically reestablish the connections after they are cut off when the number of routes exceeds the set threshold.";
                  ext:allowDelete "true";
                }
                leaf rtUpdtInterval {
                  when "not(../../../afType='ipv4vpnmcast') or ../../../afType!='ipv6vpn' and ../../../afType!='ipv4vpn' and ../../../afType!='ipv4flow' and ../../../afType!='l2vpnad' and ../../../afType!='evpn' and ../../../afType!='mvpn' and ../../../afType!='ipv4vpnmcast'";
                  type uint16 {
                    range "0..600";
                  }
                  description
                    "Specify the minimum interval at which Update packets are sent. The value is an integer, in seconds. By default, the interval at which Update packets are sent to IBGP peers is 15s, and the interval at which Update packets are sent to EBGP peers is 30s. When routes change, a router will send Update packets to notify its peers. If a route changes frequently, you can set an interval at which Update packets are sent to prevent the router from sending Update packets each time the route changes. This configuration is valid only to the routes learned from peers. ";
                  ext:allowDelete "true";
                }
                leaf redirectIP {
                  when "../../../afType='ipv4flow' and ../../../../../vrfName='_public_'";
                  type boolean;
                  default "false";
                  description
                    "After configuration commands, peer can handle the extended community attribute redirect-ip.";
                  ext:allowDelete "true";
                }
                leaf redirectIPVaildation {
                  when "../../../afType='ipv4flow'";
                  type boolean;
                  default "false";
                  description
                    "Indicate whether validation redirect ip, and this command only support ipv4-family flow address family";
                  ext:allowDelete "true";
                }
                leaf reflectClient {
                  type boolean;
                  must "not(../advBestExternal='true') or (../advBestExternal='true' and ../reflectClient='false')";
                  default "false";
                  description
                    "Configure the local device as a route reflector (RR) and a peer or peer group as its client. By default, the RR and its client are not configured. This configuration is applicable between IBGP peers only. The configurations of RRs and its clients in an address family are valid only in this address family. Therefore, it is recommended to configure RRs and its clients in the specified address family that is required.";
                  ext:allowDelete "true";
                }
                leaf substituteAsEnable {
                  when "../../../afType!='ipv4multi' and ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls'";
                  type boolean;
                  default "false";
                  description
                    "Replace the AS number of a specified peer in the AS_Path attribute with the local AS number. By default, the AS number replacement is disabled. On a PE where AS number replacement is enabled, if an AS number in the AS_Path attribute of a route is same as that of the CE to which the PE advertises the route, the PE replaces the AS number with its own AS number before advertising the route.";
                  ext:allowDelete "true";
                }
                leaf importRtPolicyName {
                  when "not(../importRtFilterName)";
                  type leafref {
                    path "/rtp:rtp/rtp:routePolicys/rtp:routePolicy/rtp:name";
                  }
                  description
                    "Specify the filtering policy applied to the routes learned from a peer. By default, no such policy is specified.";
                  ext:allowDelete "true";
                }
                leaf exportRtPolicyName {
                  when "not(../exportRtFilterName)";
                  type leafref {
                    path "/rtp:rtp/rtp:routePolicys/rtp:routePolicy/rtp:name";
                  }
                  description
                    "Specify the filtering policy applied to the routes to be advertised to a peer. By default, no such policy is specified.";
                  ext:allowDelete "true";
                }
                leaf importPrefFiltName {
                  when "not(../../../afType!='ipv4uni' and ../../../afType!='ipv4multi' and ../../../afType!='ipv4vpn' and ../../../afType!='mdt' or ../../../afType='ipv4vpnmcast') or ../../../afType='mdt'";
                  type ipPrefix {
                    length "1..169";
                    pattern '([^\? ]+)';
                  }
                  description
                    "Specify the IPv4 filtering policy applied to the routes received from a specified peer. By default, no such policy is specified.";
                  ext:allowDelete "true";
                }
                leaf importPref6FiltName {
                  when "not(../../../afType!='ipv6uni' and ../../../afType!='ipv6vpn' or ../../../afType='ipv4vpnmcast' or ../../../afType='mdt')";
                  type ipPrefix {
                    length "1..169";
                    pattern '([^\? ]+)';
                  }
                  description
                    "Specify the IPv6 filtering policy applied to the routes received from a specified peer. By default, no such policy is specified.";
                  ext:allowDelete "true";
                }
                leaf exportPrefFiltName {
                  when "not(../../../afType!='ipv4uni' and ../../../afType!='ipv4multi' and ../../../afType!='ipv4vpn' and ../../../afType!='mdt' or ../../../afType='ipv4vpnmcast' or ../../../afType='mdt')";
                  type ipPrefix {
                    length "1..169";
                    pattern '([^\? ]+)';
                  }
                  description
                    "Specify the IPv4 filtering policy applied to the routes to be advertised to a specified peer. By default, no such policy is specified.";
                  ext:allowDelete "true";
                }
                leaf exportPref6FiltName {
                  when "not(../../../afType!='ipv6uni' and ../../../afType!='ipv6vpn' or ../../../afType='ipv4vpnmcast' or ../../../afType='mdt')";
                  type ipPrefix {
                    length "1..169";
                    pattern '([^\? ]+)';
                  }
                  description
                    "Specify the IPv6 filtering policy applied to the routes to be advertised to a specified peer. By default, no such policy is specified.";
                  ext:allowDelete "true";
                }
                leaf importAsPathNameOrNum {
                  when "not(../../../afType='ipv4vpnmcast' or ../../../afType='mdt') or ../../../afType!='ipv4flow' and ../../../afType!='l2vpnad' and ../../../afType!='evpn' and ../../../afType!='ls'";
                  type leafref {
                    path "/rtp:rtp/rtp:asPathFilters/rtp:asPathFilter/rtp:index";
                  }
                  description
                    "Apply an AS_Path-based filtering policy to the routes received from a specified peer. The policy can be identified with a name or number, and the number ranges from 1 to 256. By default, no such policy is specified. Therefore, all BGP routes can be accepted.";
                  ext:allowDelete "true";
                }
                leaf exportAsPathNameOrNum {
                  when "not(../../../afType='ipv4vpnmcast' or ../../../afType='mdt') or ../../../afType!='ipv4flow' and ../../../afType!='l2vpnad' and ../../../afType!='evpn' and ../../../afType!='ls'";
                  type leafref {
                    path "/rtp:rtp/rtp:asPathFilters/rtp:asPathFilter/rtp:index";
                  }
                  description
                    "Apply an AS_Path-based filtering policy to the routes to be advertised to a specified peer. The policy can be identified with a name or number, and the number ranges from 1 to 256. By default, no such policy is specified. Therefore, all BGP routes can be advertised.";
                  ext:allowDelete "true";
                }
                leaf importAclNameOrNum {
                  when "not(../../../afType!='ipv4uni' and ../../../afType!='ipv4multi' and ../../../afType!='ipv4vpn' and ../../../afType!='mdt' or ../../../afType='ipv4vpnmcast') or ../../../afType='mdt'";
                  type leafref {
                    path "/acl:acl/acl:aclGroups/acl:aclGroup/acl:aclNumOrName";
                  }
                  description
                    "Apply an IPv4 ACL-based filtering policy to the routes received from a specified peer. The ACL number ranges from 2000 to 2999, and the name must start with a letter. By default, no such policy is specified. Therefore, all BGP routes can be accepted.";
                  ext:allowDelete "true";
                }
                leaf importAcl6NameOrNum {
                  when "not(../../../afType!='ipv6uni' and ../../../afType!='ipv6vpn' or ../../../afType='ipv4vpnmcast' or ../../../afType='mdt')";
                  type acl6NumOrName {
                    length "1..32";
                    pattern '(^2[0-9]{3}$)|(^[a-zA-Z]([^\s]*$))';
                  }
                  description
                    "Apply an IPv6 ACL-based filtering policy to the routes received from a specified peer. The ACL number ranges from 2000 to 2999, and the name must start with a letter. By default, no such policy is specified. Therefore, all BGP routes can be accepted.";
                  ext:allowDelete "true";
                }
                leaf exportAclNameOrNum {
                  when "not(../../../afType!='ipv4uni' and ../../../afType!='ipv4multi' and ../../../afType!='ipv4vpn' and ../../../afType!='mdt' or ../../../afType='ipv4vpnmcast' or ../../../afType='mdt')";
                  type leafref {
                    path "/acl:acl/acl:aclGroups/acl:aclGroup/acl:aclNumOrName";
                  }
                  description
                    "Apply an IPv4 ACL-based filtering policy to the routes to be advertised to a specified peer. The ACL number ranges from 2000 to 2999, and the name must start with a letter. By default, no such policy is specified. Therefore, all BGP routes can be advertised.";
                  ext:allowDelete "true";
                }
                leaf exportAcl6NameOrNum {
                  when "not(../../../afType!='ipv6uni' and ../../../afType!='ipv6vpn' or ../../../afType='ipv4vpnmcast' or ../../../afType='mdt')";
                  type acl6NumOrName {
                    length "1..32";
                    pattern '(^2[0-9]{3}$)|(^[a-zA-Z]([^\s]*$))';
                  }
                  description
                    "Apply an IPv6 ACL-based filtering policy to the routes to be advertised to a specified peer. The ACL number ranges from 2000 to 2999, and the name must start with a letter. By default, no such policy is specified. Therefore, all BGP routes can be advertised.";
                  ext:allowDelete "true";
                }
                leaf ipprefixOrfEnable {
                  when "not(../../../afType='ipv4vpnmcast' or ../../../afType='mdt') or ../../../afType='ipv4uni'";
                  type boolean;
                  must "not(../isNonstdIpprefixMod='true')";
                  default "false";
                  description
                    "Enable Prefix-based BGP outbound route filtering (ORF). By default, this function is not enabled. ORF enables a BGP device to use the import policy of a peer as the local export policy so that unwanted routes are filtered out during route advertisement.";
                  ext:allowDelete "true";
                }
                leaf isNonstdIpprefixMod {
                  when "not(../../../afType='ipv4vpnmcast' or ../../../afType='mdt') or ../../../afType='ipv4uni'";
                  type boolean;
                  must "not(../ipprefixOrfEnable='true')";
                  default "false";
                  description
                    "Enable Huawei routers to be compatible with Nonstandard routers. The ORF capability codes supported by Nonstandard devices are different from that defined by the associated RFC standard. After the option is selected, Huawei devices and Nonstandard devices negotiate ORF capability based on the ORF capability code supported by Nonstandard devices. If the option is not selected, Huawei devices and Nonstandard devices negotiate ORF capability based on the ORF capability code specified by the RFC standard.";
                  ext:allowDelete "true";
                }
                leaf orftype {
                  when "not(../../../afType='ipv4vpnmcast' or ../../../afType='mdt') or ../../../afType='ipv4uni'";
                  type uint16;
                  description
                    "ORF Type.";
                  ext:allowDelete "true";
                }
                leaf orfMode {
                  when "not(../../../afType='ipv4vpnmcast' or ../../../afType='mdt') or ../../../afType='ipv4uni'";
                  type bgpcommonOrfMode;
                  must "(../ipprefixOrfEnable!='true' and ../isNonstdIpprefixMod!='true' and (../orfMode='null') ) or ((not(../ipprefixOrfEnable!='true' and ../isNonstdIpprefixMod!='true') and (../orfMode='receive' or ../orfMode='send' or ../orfMode='both') ))";
                  default "null";
                  description
                    "Configure an outbound route filtering (ORF) mode, which can be Receive, Send, or Both, and the default ORF mode is Both. ";
                  ext:allowDelete "true";
                }
                leaf soostring {
                  when "not(../../../afType='ipv4vpnmcast' or ../../../afType='mdt') or ../../../../../vrfName!='_public_' or ../../../afType!='ipv4multi' and ../../../afType!='ipv4vpn' and ../../../afType!='ipv6vpn' and ../../../afType!='ipv4flow' and ../../../afType!='l2vpnad' and ../../../afType!='mvpn' and ../../../afType!='evpn' and ../../../../../vrfName!='_public_' or ../../../afType!='ipv4multi' and ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls'";
                  type string {
                    length "3..21";
                  }
                  description
                    "Configure the Site-of-Origin (SoO) extended community attribute. This attribute can be expressed in the following formats: X.X.X.X:number<0-65535>, number<0-65535>:number<0-4294967295>, or number<0-65535>.number<0-65535>:number<0-65535>  or <65536-4294967295>:<0-65535>. 0:0 or 0.0:0 is not supported. 
Two CEs are in the same site and can advertise routes to each other, and they are connected to a VPN through PEs. If the local routes of a CE are advertised to the other CE over the VPN, a routing loop may occur. 
The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops. ";
                  ext:allowDelete "true";
                }
                leaf defaultRtAdvEnable {
                  when "not(../../../afType!='ipv4uni' and ../../../afType!='ipv4multi' and ../../../afType!='ipv6uni' or ../../../afType='ipv4vpnmcast' or ../../../afType='mdt')";
                  type boolean;
                  default "false";
                  description
                    "Enable a device to advertise the default route to its peers. By default, the device does not advertise the default route to any peer or peer group. This option enables a device to send a default route with the device as the next hop address to its peers, regardless of whether there is a default route in the local routing table.";
                  ext:allowDelete "true";
                }
                leaf defaultRtAdvPolicy {
                  when "not(../../../afType!='ipv4uni' and ../../../afType!='ipv4multi' and ../../../afType!='ipv6uni' or ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls' and ../defaultRtAdvEnable='false' or ../../../afType='ipv4vpnmcast' or ../../../afType='mdt') or ../../../afType!='ipv4vpn' and ../../../afType!='ipv6vpn' and ../../../afType!='ipv4flow' and ../../../afType!='l2vpnad' and ../../../afType!='mvpn' and ../../../afType!='evpn' and ../../../afType!='ipv4vpnmcast' and ../../../afType!='mdt' and ../../../afType!='ls' and ../defaultRtAdvEnable='true'";
                  type policyName {
                    length "1..200";
                    pattern '([^\? ]+)';
                  }
                  description
                    "Specify the name of a used policy. The value is a string.";
                  ext:allowDelete "true";
                }
                leaf defaultRtMatchMode {
                  when "not(../../../afType='ipv4vpnmcast' or ../../../afType='mdt') or ../../../afType='ipv4uni' and ../defaultRtAdvEnable='true'";
                  type bgpcommonCraMatchMode;
                  default "null";
                  description
                    "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  ext:allowDelete "true";
                }
                leaf originAsValid {
                  when "not(../../../afType='ipv4vpnmcast' or ../../../afType='mdt') or ../advertiseExtCommunity='true' and ../../../afType!='ipv4multi' and ../../../afType!='ipv4flow' and ../../../afType!='l2vpnad' and ../../../afType!='mvpn' and ../../../afType!='evpn' and ../../../afType!='ipv4vpnmcast' and ../../../afType!='mdt' and ../../../afType!='ls'";
                  type boolean;
                  default "false";
                  description
                    "Advertises the BGP origin AS validation result to the specified BGP peer or peer group.";
                  ext:allowDelete "true";
                }
                leaf updatePktStandardCompatible {
                  when "../../../afType='ipv4vpnmcast'";
                  type boolean;
                  default "false";
                  description
                    "Compatible Standard update packet";
                  ext:allowDelete "true";
                }
                container peerAFCraPres {
                  when "not(../../../afType='ipv4vpnmcast' or ../../../afType='mdt')";
                  must "not(not(../defaultRtMatchMode)) or (not(../defaultRtMatchMode) and count(peerAFCraPre)>=1)";
                  description
                    "Configure the matching conditions for default route advertisement. (Only the default routes that match the conditions can be advertised.)";
                  list peerAFCraPre {
                    when "not(../../defaultRtMatchMode) and ../../../../afType='ipv4uni'";
                    key "defaultRtAddress defaultRtMask";
                    max-elements  "4";
                    description
                      "Configure the matching condition for default route advertisement.";
                    leaf defaultRtAddress {
                      type inet:ipv4-address-no-zone;
                      description
                        "Configure a prefix that is used to match default routes.";
                    }
                    leaf defaultRtMask {
                      type uint32 {
                        range "0..32";
                      }
                      description
                        "Configure a mask that is used to match default routes.";
                    }
                  }
                }
                container statisticsInfo {
                  config false;
                  description
                    "Route statistics.";
                  leaf recvNLRINum {
                    type uint32 {
                      range "0..4294967295";
                    }
                    config false;
                    description
                      "Number of reachable routes.";
                  }
                  leaf recvUNLRINum {
                    type uint32 {
                      range "0..4294967295";
                    }
                    config false;
                    description
                      "Number of unreachable routes.";
                  }
                  leaf prePlyRouteNum {
                    type uint32 {
                      range "0..4294967295";
                    }
                    config false;
                    description
                      "Number of accepted routes.";
                  }
                  leaf postPlyRouteNum {
                    type uint32 {
                      range "0..4294967295";
                    }
                    config false;
                    description
                      "Number of received routes.";
                  }
                  leaf bestRouteNum {
                    type uint32 {
                      range "0..4294967295";
                    }
                    config false;
                    description
                      "Number of optimal routes.";
                  }
                  leaf rejectedRtNum {
                    type uint32 {
                      range "0..4294967295";
                    }
                    config false;
                    description
                      "Number of rejected routes.";
                  }
                  leaf asPathLoopRtNum {
                    type uint32 {
                      range "0..4294967295";
                    }
                    config false;
                    description
                      "Number of routing loops in an AS.";
                  }
                  leaf asConfLoopRtNum {
                    type uint32 {
                      range "0..4294967295";
                    }
                    config false;
                    description
                      "Number of routing loops in an AS confederation.";
                  }
                  leaf cluLoopRtNum {
                    type uint32 {
                      range "0..4294967295";
                    }
                    config false;
                    description
                      "Number of routing loops in a cluster.";
                  }
                  leaf invalOrigRtNum {
                    type uint32 {
                      range "0..4294967295";
                    }
                    config false;
                    description
                      "Number of routes with an invalid originator ID.";
                  }
                }
                container peerInfo {
                  config false;
                  description
                    "Peer information.";
                  leaf peerType {
                    type bgpcommPeerType;
                    config false;
                    description
                      "Configures the type of BGP peers: IBGP or EBGP.";
                  }
                  leaf version {
                    type uint8;
                    config false;
                    description
                      "The current BGP version is BGP-4. BGP-4 provides a set of new mechanisms to support Classless Inter-Domain Routing (CIDR). The new mechanisms also support the network prefix-based advertisement, cancellation of the 'class' concept for a BGP network during the network prefix-supported advertisements, and route summarization and AS path summarization.";
                  }
                  leaf remoteRouterId {
                    type inet:ipv4-address-no-zone;
                    config false;
                    description
                      "Router ID for a peer.";
                  }
                  leaf bgpCurState {
                    type bgpcommPEERSTATE;
                    config false;
                    description
                      "Current BGP state, which can be Idle, Active, Established, Connect, OpenSent, or OpenConfirm.
Idle: In this state, BGP denies all connection requests. This is the initial state of BGP.
Active: In this state, BGP tries to establish TCP connections. This is the intermediate state of BGP.
Established: In this state, BGP peers can exchange Update, Notification, and Keepalive packets with each other.
Connect: In this state, BGP determines the subsequent operation after the TCP connections are established.
OpenSent: In this state, BGP is waiting for the Open packet from the peer.
OpenConfirm: In this state, BGP is waiting for a Notification packet and a Keepalive packet.";
                  }
                  leaf localPort {
                    type uint32;
                    config false;
                    description
                      "Local port number. BGP uses the TCP as the transport layer protocol, and the port number is 179.";
                  }
                  leaf remotePort {
                    type uint32 {
                      range "0..4294967295";
                    }
                    config false;
                    description
                      "Port number for a peer to establish a peer relationship.";
                  }
                  leaf currentEvent {
                    type string {
                      length "0..39";
                    }
                    config false;
                    description
                      "Recent event that occurs on a peer.";
                  }
                  leaf bgpLastState {
                    type bgpcommPEERSTATE;
                    config false;
                    description
                      "Last state of a peer, which can be Idle, Connect, Active, OpenSent, OpenConfirm, or Established.";
                  }
                  leaf upDownDuration {
                    type string {
                      length "0..49";
                    }
                    config false;
                    description
                      "Period during which a BGP session is in the established state.";
                  }
                  leaf messageSent {
                    type uint32 {
                      range "0..4294967295";
                    }
                    config false;
                    description
                      "Number of packets sent to a peer.";
                  }
                  leaf messageReceived {
                    type uint32 {
                      range "0..4294967295";
                    }
                    config false;
                    description
                      "Number of packets received from a peer.";
                  }
                  leaf outQueue {
                    type uint32 {
                      range "0..4294967295";
                    }
                    config false;
                    description
                      "Number of packets to be sent in a queue.";
                  }
                  leaf revHoldTime {
                    type uint32 {
                      range "0..65535";
                    }
                    config false;
                    description
                      "Hold time of a peer.";
                  }
                  leaf revLastKeepAliveTime {
                    type yang:date-and-time;
                    config false;
                    description
                      "Last time when Keepalive packets were received from a peer.";
                  }
                  leaf negoHoldTime {
                    type uint32 {
                      range "0..65535";
                    }
                    config false;
                    description
                      "Hold time negotiated by BGP peers.";
                  }
                  leaf negoKeepAliveTime {
                    type uint32 {
                      range "0..21845";
                    }
                    config false;
                    description
                      "Keepalive time negotiated by BGP peers.";
                  }
                  leaf revUpdateCount {
                    type uint32 {
                      range "0..4294967295";
                    }
                    config false;
                    description
                      "Number of Update packets received from a peer.";
                  }
                  leaf revOpenCount {
                    type uint32 {
                      range "0..4294967295";
                    }
                    config false;
                    description
                      "Number of Open packets received from a peer.";
                  }
                  leaf revKeepAliveCount {
                    type uint32 {
                      range "0..4294967295";
                    }
                    config false;
                    description
                      "Number of Keepalive packets received from a peer.";
                  }
                  leaf revNotificationCount {
                    type uint32 {
                      range "0..4294967295";
                    }
                    config false;
                    description
                      "Number of Notification packets received from a peer.";
                  }
                  leaf revRouteRefreshCount {
                    type uint32 {
                      range "0..4294967295";
                    }
                    config false;
                    description
                      "Number of Route-Refresh packets received from a peer.";
                  }
                  leaf sentUpdateCount {
                    type uint32 {
                      range "0..4294967295";
                    }
                    config false;
                    description
                      "Number of Update packets sent to a peer.";
                  }
                  leaf sentOpenCount {
                    type uint32 {
                      range "0..4294967295";
                    }
                    config false;
                    description
                      "Number of Open packets sent to a peer.";
                  }
                  leaf sentKeepAliveCount {
                    type uint32 {
                      range "0..4294967295";
                    }
                    config false;
                    description
                      "Number of Keepalive packets sent to a peer.";
                  }
                  leaf sentNotificationCount {
                    type uint32 {
                      range "0..4294967295";
                    }
                    config false;
                    description
                      "Number of Notification packets sent to a peer.";
                  }
                  leaf sentRouteRefreshCount {
                    type uint32 {
                      range "0..4294967295";
                    }
                    config false;
                    description
                      "Number of Route-Refresh packets sent to a peer.";
                  }
                  leaf sendGRCapability {
                    type boolean;
                    config false;
                    description
                      "Whether the local end supports RR.";
                  }
                  leaf revRefreshCapability {
                    type boolean;
                    config false;
                    description
                      "Whether the peer supports RR.";
                  }
                  leaf revFourByteASCapability {
                    type boolean;
                    config false;
                    description
                      "Whether the peer supports 4-byte AS numbers.";
                  }
                  leaf revSupportMPCapability {
                    type boolean;
                    config false;
                    description
                      "Whether the peer supports MP.";
                  }
                  leaf revGRCapability {
                    type boolean;
                    config false;
                    description
                      "Whether the peer supports GR.";
                  }
                  leaf prefRecv {
                    type uint32 {
                      range "0..4294967295";
                    }
                    config false;
                    description
                      "Number of received route prefixes.";
                  }
                  leaf activePrefRecv {
                    type uint32 {
                      range "0..4294967295";
                    }
                    config false;
                    description
                      "Number of received prefixes of active routes.";
                  }
                  leaf prefAdvertised {
                    type uint32 {
                      range "0..4294967295";
                    }
                    config false;
                    description
                      "Number of advertised route prefixes.";
                  }
                }
              }
            }
            container importRoutes {
              when "not(../afType='ipv4vpnmcast' or ../afType='mdt')";
              description
                "List of imported routes.";
              list importRoute {
                when "../../afType!='ipv4vpn' and ../../afType!='ipv6vpn' and ../../afType!='ipv4flow' and ../../afType!='l2vpnad' and ../../afType!='mvpn' and ../../afType!='evpn' and ../../afType!='ipv4vpnmcast' and ../../afType!='mdt' and ../../afType!='ls'";
                key "importProtocol importProcessId";
                description
                  "Route import. Routes of other protocol types can be imported by BGP. By default, BGP does not import routes of other protocol types.";
                leaf importProtocol {
                  type bgpcommImRouteProtocol;
                  description
                    "Routing protocol from which routes can be imported. The routing protocol can be IS-IS, OSPF, static, direct, or RIP for an IPv4 unicast address family or an IPv4 multicast address family. The routing protocol can be IS-IS, OSPFv3, static, direct, or RIPng for an IPv6 uincast address family.";
                }
                leaf importProcessId {
                  type uint32 {
                    range "0..4294967295";
                  }
                  description
                    "Process ID of an imported routing protocol. The process ID must be specified if the imported routing protocol is RIP, OSPF, RIPng, or OSPFv3.";
                }
                leaf importRoutePolicy {
                  when "not(../routeFilterName)";
                  type policyName {
                    length "1..200";
                    pattern '([^\? ]+)';
                  }
                  description
                    "When routes are imported from other routing protocols, the route-policy filter can be used to filter the routes and change route attributes.";
                  ext:allowDelete "true";
                }
                leaf medNew {
                  type uint64 {
                    range "0..4294967295";
                  }
                  description
                    "Specify the MED of imported routes.";
                  ext:allowDelete "true";
                }
              }
            }
            container networkRoutes {
              when "not(../afType='ipv4vpnmcast' or ../afType='mdt')";
              description
                "List of advertised routes.";
              list networkRoute {
                when "../../afType!='ipv4vpn' and ../../afType!='ipv6vpn' and ../../afType!='ipv4flow' and ../../afType!='l2vpnad' and ../../afType!='mvpn' and ../../afType!='evpn' and ../../afType!='ipv4vpnmcast' and ../../afType!='mdt' and ../../afType!='ls'";
                key "networkAddress maskLen";
                description
                  "Configure the local routes that can be advertised by BGP. That is, add the routes in the local routing table to the BGP routing table in static mode and send them to the peer end. By default, BGP does not advertise any local route.";
                leaf networkAddress {
                  type inet:ip-address-no-zone;
                  description
                    "Specify the IP address advertised by BGP. An IPv4 address can be configured in the IPv4 address family, in dotted decimal notation, and an IPv6 routes can be configured in the IPv6 address family. Note: During the configuration of a network route, the IP address is adjusted based on the mask. It is recommended that you click Synchronize All after creating a network route.";
                }
                leaf maskLen {
                  type uint8 {
                    range "0..128";
                  }
                  description
                    "Specify the mask length of an IP address. The mask length ranges from 0 to 32 for an IPv4 address, and ranges from 0 to 128 for an IPv6 address.";
                }
                leaf networkPolicy {
                  when "not(../routeFilterName)";
                  type policyName {
                    length "1..200";
                    pattern '([^\? ]+)';
                  }
                  description
                    "Specify the route-policy for route advertisement. The value is a string.";
                  ext:allowDelete "true";
                }
              }
            }
            container aggregateRoutes {
              when "not(../afType='ipv4vpnmcast' or ../afType='mdt')";
              description
                "List of summarized routes.";
              list aggregateRoute {
                when "../../afType!='ipv4vpn' and ../../afType!='ipv6vpn' and ../../afType!='ipv4flow' and ../../afType!='l2vpnad' and ../../afType!='mvpn' and ../../afType!='evpn' and ../../afType!='ipv4vpnmcast' and ../../afType!='mdt' and ../../afType!='ls'";
                key "aggreAddress maskLength";
                description
                  "Create a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of  complete > egp > igp. A summarized route carries the community attribute of each specific route.";
                leaf aggreAddress {
                  type inet:ip-address-no-zone;
                  description
                    "Specify the IPv4 address or IPv6 address of a summarized route. Only IPv4 summarized routes can be configured in the IPv4 address family and only IPv6 summarized routes can be configured in the IPv6 address family.";
                }
                leaf maskLength {
                  type uint8 {
                    range "0..128";
                  }
                  description
                    "Specify the mask length of a summarized address. The mask length ranges from 0 to 32 for an IPv4 address, and ranges from 0 to 128 for an IPv6 address.";
                }
                leaf asSetEnable {
                  type boolean;
                  default "false";
                  description
                    "Generate routes with the AS-SET attribute. This option can be used to create a summarized route. The AS_Path attribute of the summarized route contains the AS-Path attributes of the specific routes for the route summarization. Exercise caution when using this option if multiple AS_Paths need to be summarized to prevent route flapping. ";
                }
                leaf detailSuppressed {
                  type boolean;
                  default "false";
                  description
                    "Suppress the advertisement of specific routes for the route summarization. Only the summarized route is advertised.";
                }
                leaf attributePolicy {
                  when "not(../attrFilterName or ../origFilterName or ../suppFilterName)";
                  type policyName {
                    length "1..200";
                    pattern '([^\? ]+)';
                  }
                  description
                    "Specify an attribute of summarized routes. If apply as-path is used to configure the AS_Path attribute that is used in the route Summarization policy, and the as-set keyword is set, the AS_Path attribute in the policy does not take effect.";
                  ext:allowDelete "true";
                }
                leaf originPolicy {
                  when "not(../attrFilterName or ../origFilterName or ../suppFilterName)";
                  type policyName {
                    length "1..200";
                    pattern '([^\? ]+)';
                  }
                  description
                    "Specify the name of a policy for generating summarized routes. Summarized routes are generated only when the routes match route-policy.";
                  ext:allowDelete "true";
                }
                leaf suppressPolicy {
                  when "not(../attrFilterName or ../origFilterName or ../suppFilterName)";
                  type policyName {
                    length "1..200";
                    pattern '([^\? ]+)';
                  }
                  description
                    "Specify a policy for suppressing the advertisement of specified routes. The routes matching the policy are not advertised, and other routes are advertised.";
                  ext:allowDelete "true";
                }
              }
            }
            container dampRoutes {
              when "not(../afType='ipv4vpnmcast' or ../afType='mdt')";
              description
                "List of route dampening.";
              list dampRoute {
                when "../../afType!='ipv4vpn' and ../../afType!='ipv6vpn' and ../../afType!='ipv4flow' and ../../afType!='l2vpnad' and ../../afType!='mvpn' and ../../afType!='evpn' and ../../afType!='ipv4vpnmcast' and ../../afType!='mdt' and ../../afType!='ls'";
                key "halfLifeReachTime reuse suppress ceiling peerType";
                description
                  "Enable BGP route dampening or modify various BGP route dampening parameters. By default, route dampening is not configured. If a suppression policy for route dampening is configured, routes are preferentially matched against the suppression parameters defined in the suppression policy. If no parameter is configured, the default value of each parameter is used. The four route dampening parameters are mutually dependent. If you configure one of the parameters, the other parameters also need to be configured. When you configure BGP route dampening, the values of reuse threshold, suppress threshold, and penalty ceiling must meet the inequality of reuse threshold < suppress threshold < penalty ceiling. If Maximum suppression time obtained by using the formula of Maximum suppression time = Half life (of reachable routes) x 60 x (ln(Penalty ceiling/Reuse threshold)/ln(2)) is smaller than 1, suppression cannot be performed. Ensure that the value of the maximum suppression time is equal to or greater than 1. This means that the value of the penalty ceiling/reuse threshold must be great enough.";
                leaf halfLifeReachTime {
                  type uint16 {
                    range "1..45";
                  }
                  description
                    "Configure a half-life for reachable routes. The value is an integer, in minutes. The default value is 15.";
                }
                leaf reuse {
                  type uint16 {
                    range "1..20000";
                  }
                  description
                    "Configure a threshold for a route to be unsuppressed. If the penalty value of the route falls below the threshold, the route is reused. The threshold value is an integer. The default value is 750.  ";
                }
                leaf suppress {
                  type uint16 {
                    range "1..20000";
                  }
                  description
                    "Configure a threshold for a route to be suppressed.  When the penalty value of the route exceeds the suppression threshold, the route is suppressed.  The configured suppression threshold must be greater than the reuse threshold. The value of the suppression threshold is an integer. The default value is 2000.";
                }
                leaf ceiling {
                  type uint16 {
                    range "1001..20000";
                  }
                  description
                    "Configure the penalty ceiling. The configured threshold must be greater than the suppression threshold. The value of the penalty ceiling is an integer. The default value is 16000.";
                }
                leaf dampPolicyName {
                  when "not(../dampFilterName)";
                  type policyName {
                    length "1..200";
                    pattern '([^\? ]+)';
                  }
                  description
                    "Configure a suppression policy for route dampening. You can use a routing policy to select the routes to be suppressed.";
                  ext:allowDelete "true";
                }
                leaf updateStandard {
                  type boolean;
                  description
                    "Update Standard.";
                }
                leaf peerType {
                  type uint8 {
                    range "0..1";
                  }
                  description
                    "Configure the peer type. The value of the penalty ceiling is an integer. The default value is 0(0:EBGP, 1:IBGP).";
                }
              }
            }
            container filterPolicys {
              when "not(../afType='ipv4vpnmcast' or ../afType='ls' or ../afType='mdt') or ../afType!='l2vpnad' and ../afType!='ipv4vpnmcast' and ../afType!='mdt' and ../afType!='ls'";
              description
                "List of filtering policies.";
              list filterPolicy {
                when "not(../../afType='evpn' or ../../afType='ipv4vpnmcast' or ../../afType='l2vpnad' or ../../afType='ls' or ../../afType='mdt' or ../../afType='mvpn') or ../../afType!='l2vpnad' and ../../afType!='ipv4vpnmcast' and ../../afType!='mdt' and ../../afType!='ls'";
                key "filterProtocol filterProcessId import export";
                description
                  "Specify a filtering policy. It is used to filter the routes received from a peer and the routes to be advertised to the peer. By default, routes are not filtered.";
                leaf filterProtocol {
                  type bgpcommFilterProtocol;
                  description
                    "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                }
                leaf filterProcessId {
                  type uint32 {
                    range "0..4294967295";
                  }
                  description
                    "Specify the process ID required to be matched. The value is an integer ranging from 1 to 65535. If direct or static routes need to be filtered, no process ID is required.";
                }
                leaf import {
                  type boolean;
                  description
                    "Filter received routes. Only the routes that match the policy can be added to the BGP routing table. When a rule is configured for a named ACL, only the source address range specified by the source parameter and the time period specified by the time-range parameter take effect.";
                }
                leaf export {
                  type boolean;
                  description
                    "Filter routes to be advertised. Only the routes that match the policy can be advertised by BGP. After the filtering function is configured, routes are filtered before being imported by BGP. Only the routes that match the policy can be added to the local BGP routing table and advertised by BGP. If a routing protocol is specified, only the routes of this protocol are filtered, and the routes of other protocols are not filtered. If no routing protocol is specified, all protocol routes are filtered. When a rule is configured for a named ACL, only the source address range specified by the source parameter and the time period specified by the time-range parameter take effect.";
                }
                leaf aclNameOrNum {
                  when "../../../afType!='ipv6uni' and ../../../afType!='ipv6vpn'";
                  type leafref {
                    path "/acl:acl/acl:aclGroups/acl:aclGroup/acl:aclNumOrName";
                  }
                  description
                    "Specify the name or number of an ACL Rule. The number value ranges from 2000 to 2999 and is used by basic ACL rules. The name must start with a letter, and the name is case-sensitive.";
                  ext:allowDelete "true";
                }
                leaf acl6NameOrNum {
                  when "not(../../../afType!='ipv6uni' and ../../../afType!='ipv6vpn')";
                  type acl6NumOrName {
                    length "1..32";
                    pattern '(^2[0-9]{3}$)|(^[a-zA-Z]([^\s]*$))';
                  }
                  description
                    "Specify the name or number of an ACL6 Rule. The number value ranges from 2000 to 2999 and is used by basic ACL6 rules. The name must start with a letter, and the name is case-sensitive.";
                  ext:allowDelete "true";
                }
                leaf preFlt4Name {
                  when "../../../afType!='ipv6uni' and ../../../afType!='ipv6vpn'";
                  type ipPrefix {
                    length "1..169";
                    pattern '([^\? ]+)';
                  }
                  description
                    "Specify the IPv4 prefix list name.";
                  ext:allowDelete "true";
                }
                leaf preFlt6Name {
                  when "not(../../../afType!='ipv6uni' and ../../../afType!='ipv6vpn')";
                  type ipPrefix {
                    length "1..169";
                    pattern '([^\? ]+)';
                  }
                  description
                    "Specify the IPv6 prefix list name.";
                  ext:allowDelete "true";
                }
              }
            }
            container instanceImports {
              when "not(../afType='ipv4vpnmcast' or ../afType='mdt')";
              description
                "List of Instance Imported Routes.";
              list instanceImport {
                when "../../afType!='ipv4vpn' and ../../afType!='ipv6vpn' and ../../afType!='ipv4flow' and ../../afType!='l2vpnad' and ../../afType!='mvpn' and ../../afType!='evpn' and ../../afType!='ipv4vpnmcast' and ../../afType!='ipv4multi' and ../../afType!='mdt' and ../../afType!='ls'";
                key "srcVrfName";
                description
                  "Instance Imported Route.";
                leaf srcVrfName {
                  type leafref {
                    path "/l3vpn:l3vpn/l3vpn:l3vpncomm/l3vpn:l3vpnInstances/l3vpn:l3vpnInstance/l3vpn:vrfName";
                  }
                  description
                    "Source VRF Name For Instance Imported Route.";
                }
                leaf policyName {
                  when "not(../routeFilterName)";
                  type policyName {
                    length "1..200";
                    pattern '([^\? ]+)';
                  }
                  description
                    "Policy for Route Import.";
                  ext:allowDelete "true";
                }
                leaf validRtEnable {
                  type boolean;
                  default "false";
                  description
                    "Imported Valid Route.";
                  ext:allowDelete "true";
                }
              }
            }
            container routingTables {
              when "not(../afType='evpn')";
              config false;
              description
                "List of displayed route information in an address family.";
              list routingTable {
                when "../../afType!='ipv4flow' and ../../afType!='l2vpnad' and ../../afType!='evpn' and ../../afType!='ls'";
                key "networkPrefix prefixMask routeTypeFlag imTableId rd from pathID remoteNextHopTunnelAddress remoteNextHopMacAdress";
                config false;
                description
                  "Information about routes.";
                leaf networkPrefix {
                  type inet:ip-address-no-zone;
                  config false;
                  description
                    "BGP route prefix.";
                }
                leaf prefixMask {
                  type uint8;
                  config false;
                  description
                    "Prefix mask.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type leafref {
                    path "/ifm:ifm/ifm:interfaces/ifm:interface/ifm:ifName";
                  }
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf isAtomicAggre {
                  type boolean;
                  default "false";
                  config false;
                  description
                    "Route carrying the atomic-aggregate attribute.";
                }
                leaf aggregatorAs {
                  type string {
                    length "1..11";
                  }
                  config false;
                  description
                    "AS number of the route summarizer.";
                }
                leaf aggregatorId {
                  type inet:ip-address-no-zone;
                  config false;
                  description
                    "ID of the route summarizer.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pathID {
                  type string {
                    length "0..50";
                  }
                  config false;
                  description
                    "Path ID.";
                }
                leaf vrfName {
                  type string {
                    length "0..31";
                  }
                  config false;
                  description
                    "Iterated Vrf .";
                }
                leaf remoteNextHopTunnelAddress {
                  type inet:ip-address-no-zone;
                  config false;
                  description
                    "The remote next hop tunnel adress.";
                }
                leaf remoteNextHopVni {
                  type uint32 {
                    range "0..4294967295";
                  }
                  config false;
                  description
                    "The remote next hop vni.";
                }
                leaf remoteNextHopMacAdress {
                  type pub-type:macAddress {
                    length "0..60";
                  }
                  config false;
                  description
                    "The Remote next hop mac.";
                }
              }
            }
            container routingFlappingInfos {
              when "not(../afType='ipv4vpnmcast' or ../afType='mdt')";
              config false;
              description
                "Flapping statistics about BGP.";
              list routingFlappingInfo {
                when "not(../../afType='l2vpnad') or ../../afType!='l2vpnad' and ../../afType!='ipv4vpnmcast' and ../../afType!='mdt' and ../../afType!='ls'";
                key "networkAddress maskLength";
                config false;
                description
                  "Flapping statistics about BGP.";
                leaf networkAddress {
                  type inet:ip-address-no-zone;
                  config false;
                  description
                    "BGP route prefix.";
                }
                leaf maskLength {
                  type uint8 {
                    range "0..128";
                  }
                  config false;
                  description
                    "Mask length of an IP address.";
                }
                leaf fromPeer {
                  type inet:ip-address-no-zone;
                  config false;
                  description
                    "IP address of the peer that advertises routes.";
                }
                leaf origin {
                  type bgpcommOrigin;
                  config false;
                  description
                    "Route origin.";
                }
                leaf asPath {
                  type string {
                    length "0..10240";
                  }
                  config false;
                  description
                    "AS_Path attribute.";
                }
                leaf flaps {
                  type uint16 {
                    range "0..65535";
                  }
                  config false;
                  description
                    "Total number of route flapping times.";
                }
                leaf reuseTime {
                  type pub-type:timeTick;
                  config false;
                  description
                    "Reuse value.";
                }
                leaf durationTime {
                  type pub-type:timeTick;
                  config false;
                  description
                    "Duration that the flapping lasts.";
                }
              }
            }
            container routingDampenedInfos {
              when "not(../afType='ipv4vpnmcast' or ../afType='mdt')";
              config false;
              description
                "Statistics about dampened BGP routes.";
              list routingDampenedInfo {
                when "not(../../afType='l2vpnad') or ../../afType!='l2vpnad' and ../../afType!='ipv4vpnmcast' and ../../afType!='mdt' and ../../afType!='ls'";
                key "networkAddress maskLength";
                config false;
                description
                  "Statistics about a dampened BGP route.";
                leaf networkAddress {
                  type inet:ip-address-no-zone;
                  config false;
                  description
                    "BGP route prefix.";
                }
                leaf maskLength {
                  type uint8 {
                    range "0..128";
                  }
                  config false;
                  description
                    "Mask length of an IP address.";
                }
                leaf fromPeer {
                  type inet:ip-address-no-zone;
                  config false;
                  description
                    "IP address of the peer that advertises routes.";
                }
                leaf origin {
                  type bgpcommOrigin;
                  config false;
                  description
                    "Route origin.";
                }
                leaf asPath {
                  type string {
                    length "0..10240";
                  }
                  config false;
                  description
                    "AS_Path attribute.";
                }
                leaf reuseTime {
                  type pub-type:timeTick;
                  config false;
                  description
                    "Reuse value.";
                }
              }
            }
            container ngRoutingTable1s {
              when "not(../afType='ipv4vpnmcast' or ../afType='mdt')";
              config false;
              description
                "List of displayed BGP Ng route type 1 information.";
              list ngRoutingTable1 {
                when "../../afType='mvpn'";
                key "ngNlri rd from ngRouteType routeTypeFlag";
                config false;
                description
                  "Information about BGP Ng routes type 1.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "0..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "0..300";
                  }
                  config false;
                  description
                    "Ng Route prefix information.";
                }
                leaf ngPmsiString {
                  type string {
                    length "0..300";
                  }
                  config false;
                  description
                    "PMSI attribute.";
                }
              }
            }
            container ngRoutingTable2s {
              when "not(../afType='ipv4vpnmcast' or ../afType='mdt')";
              config false;
              description
                "List of displayed BGP Ng route type 2 information.";
              list ngRoutingTable2 {
                when "../../afType='mvpn'";
                key "ngNlri rd from ngRouteType routeTypeFlag";
                config false;
                description
                  "Information about BGP Ng routes type 2.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "0..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "0..300";
                  }
                  config false;
                  description
                    "Ng Route Prefix Information.";
                }
              }
            }
            container ngRoutingTable3s {
              when "not(../afType='ipv4vpnmcast' or ../afType='mdt')";
              config false;
              description
                "List of displayed BGP Ng route type 3 information.";
              list ngRoutingTable3 {
                when "../../afType='mvpn'";
                key "ngNlri rd from ngRouteType routeTypeFlag";
                config false;
                description
                  "Information about BGP Ng routes type 3.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "0..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "0..300";
                  }
                  config false;
                  description
                    "Ng route prefix information.";
                }
              }
            }
            container ngRoutingTable4s {
              when "not(../afType='ipv4vpnmcast' or ../afType='mdt')";
              config false;
              description
                "List of displayed BGP Ng route type 4 information.";
              list ngRoutingTable4 {
                when "../../afType='mvpn'";
                key "ngNlri rd from ngRouteType routeTypeFlag";
                config false;
                description
                  "Information about BGP Ng routes type 4.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "0..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "0..300";
                  }
                  config false;
                  description
                    "Ng route prefix information.";
                }
              }
            }
            container ngRoutingTable5s {
              when "not(../afType='ipv4vpnmcast' or ../afType='mdt')";
              config false;
              description
                "List of displayed BGP Ng route type 5 information.";
              list ngRoutingTable5 {
                when "../../afType='mvpn'";
                key "ngNlri rd from ngRouteType routeTypeFlag";
                config false;
                description
                  "Information about BGP Ng routes type 5.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "0..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "0..300";
                  }
                  config false;
                  description
                    "Ng route prefix information.";
                }
              }
            }
            container ngRoutingTable6s {
              when "not(../afType='ipv4vpnmcast' or ../afType='mdt')";
              config false;
              description
                "List of displayed BGP Ng route type 6 information.";
              list ngRoutingTable6 {
                when "../../afType='mvpn'";
                key "ngNlri rd from ngRouteType routeTypeFlag";
                config false;
                description
                  "Information about BGP Ng routes type 6.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "0..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "0..300";
                  }
                  config false;
                  description
                    "Ng route prefix information.";
                }
              }
            }
            container ngRoutingTable7s {
              when "not(../afType='ipv4vpnmcast' or ../afType='mdt')";
              config false;
              description
                "List of displayed BGP Ng route type 7 information.";
              list ngRoutingTable7 {
                when "../../afType='mvpn'";
                key "ngNlri rd from ngRouteType routeTypeFlag";
                config false;
                description
                  "Information about BGP Ng routes type 7.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "0..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "0..300";
                  }
                  config false;
                  description
                    "Ng route prefix information.";
                }
              }
            }
            container vpnv4McastRoutingTables {
              when "not(../afType='evpn') or ../afType='ipv4vpnmcast'";
              config false;
              description
                "List of displayed route information in VPNv4 Multicast address family.";
              list vpnv4McastRoutingTable {
                when "not(../../afType='evpn')";
                key "networkPrefix prefixMask routeTypeFlag imTableId rd from";
                config false;
                description
                  "Information about VPNv4 Multicast routes.";
                leaf networkPrefix {
                  type inet:ip-address-no-zone;
                  config false;
                  description
                    "BGP route prefix.";
                }
                leaf prefixMask {
                  type uint8;
                  config false;
                  description
                    "Prefix mask.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "0..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "0..100";
                  }
                  config false;
                  description
                    "Route flag that contains a string of characters.";
                }
                leaf rd {
                  type string {
                    length "0..22";
                  }
                  config false;
                  description
                    "Route distinguisher.";
                }
                leaf rtWorseReson {
                  type string {
                    length "1..50";
                  }
                  config false;
                  description
                    "Reason why a route is not selected.";
                }
                leaf peerString {
                  type string {
                    length "0..300";
                  }
                  config false;
                  description
                    "List of route sending peers.";
                }
                leaf time {
                  type uint32 {
                    range "0..4294967295";
                  }
                  config false;
                  description
                    "Time stamp of a route.";
                }
                leaf community {
                  type string {
                    length "0..120";
                  }
                  config false;
                  description
                    "Community attribute.";
                }
                leaf extCommunity {
                  type string {
                    length "0..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "0..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
              }
            }
            container bgpSlowPeerInfos {
              config false;
              description
                "Slow peer list.";
              list bgpSlowPeerInfo {
                key "remoteAddress";
                config false;
                description
                  "Slow peer information.";
                leaf remoteAddress {
                  type inet:ip-address-no-zone;
                  config false;
                  description
                    "Slow peer address.";
                }
                leaf slowLastEndTime {
                  type yang:date-and-time;
                  config false;
                  description
                    "The last time of slow neighbors as nomal.";
                }
                leaf slowStartTime {
                  type yang:date-and-time;
                  config false;
                  description
                    "The time of neighbor is detected as slow neighbor.";
                }
                leaf slowCount {
                  type uint32;
                  config false;
                  description
                    "Slow peer count.";
                }
              }
            }
          }
        }
        container bgpPeerBfdSessionInfos {
          config false;
          description
            "List of BFD sessions.";
          list bgpPeerBfdSessionInfo {
            key "remoteAddress";
            config false;
            description
              "BFD session.";
            leaf remoteAddress {
              type inet:ip-address-no-zone;
              config false;
              description
                "Peer address of the BFD session.";
            }
            leaf localAdress {
              type inet:ip-address-no-zone;
              config false;
              description
                "Local address of the BFD session.";
            }
            leaf ifName {
              type pub-type:ifName;
              config false;
              description
                "Name of an interface of the BFD session.";
            }
            leaf txInterval {
              type uint32 {
                range "0..4294967295";
              }
              default "0";
              config false;
              description
                "Interval at which BFD packets are sent, in milliseconds.";
            }
            leaf rxInterval {
              type uint32 {
                range "0..4294967295";
              }
              default "0";
              config false;
              description
                "Interval at which BFD packets are received, in milliseconds.";
            }
            leaf multiplier {
              type uint32 {
                range "0..50";
              }
              config false;
              description
                "Detection multiplier. ";
            }
            leaf sessionState {
              type bgpBfdState;
              config false;
              description
                "State of the BFD session.";
            }
            leaf bfdGlobalEnable {
              type boolean;
              config false;
              description
                "Global BFD state.";
            }
          }
        }
      }
    }
    container vrfAllRoutingTables {
      config false;
      description
        "List of displayed VPN route information.";
      list vrfAllRoutingTable {
        key "showVrfName afType networkPrefix prefixMask routeTypeFlag imTableId rd from pathID remoteNextHopTunnelAddress remoteNextHopMacAdress";
        config false;
        description
          "Information about A VPN route.";
        leaf showVrfName {
          type string {
            length "0..300";
          }
          config false;
          description
            "BGP instance name.";
        }
        leaf afType {
          type bgpcommPrefixType;
          config false;
          description
            "BGP address family type.";
        }
        leaf networkPrefix {
          type inet:ip-address-no-zone;
          config false;
          description
            "BGP route prefix.";
        }
        leaf prefixMask {
          type uint8;
          config false;
          description
            "Prefix mask.";
        }
        leaf routeTypeFlag {
          type pub-type:bits32;
          config false;
          description
            "Route type.";
          ext:masklen 32;
            ext:bit "ibgp" {
              position 0;
            }
            ext:bit "ebgp" {
              position 1;
            }
            ext:bit "network" {
              position 2;
            }
            ext:bit "import" {
              position 3;
            }
            ext:bit "auto-summary" {
              position 4;
            }
            ext:bit "aggregate" {
              position 5;
            }
            ext:bit "cpri" {
              position 6;
            }
            ext:bit "pcri" {
              position 7;
            }
            ext:bit "suppressed" {
              position 8;
            }
            ext:bit "NHP-EMPTY" {
              position 9;
            }
            ext:bit "NO-ADV" {
              position 10;
            }
            ext:bit "local_cross" {
              position 11;
            }
            ext:bit "remote_cross" {
              position 12;
            }
            ext:bit "VD-BGP" {
              position 13;
            }
            ext:bit "PATH_LOCAL" {
              position 14;
            }
            ext:bit "PATH_GATEWAY" {
              position 15;
            }
            ext:bit "policy_nopass" {
              position 16;
            }
            ext:bit "supprenet" {
              position 17;
            }
            ext:bit "dampened" {
              position 18;
            }
            ext:bit "history" {
              position 19;
            }
            ext:bit "select" {
              position 20;
            }
            ext:bit "best" {
              position 21;
            }
            ext:bit "backup" {
              position 22;
            }
            ext:bit "attr_change" {
              position 23;
            }
            ext:bit "NHLFE_CREATED" {
              position 24;
            }
            ext:bit "ILM_CREATED" {
              position 25;
            }
            ext:bit "NEXTHOP_CHANGE" {
              position 26;
            }
            ext:bit "Invaild" {
              position 27;
            }
            ext:bit "SOURCE_CHANGE" {
              position 28;
            }
            ext:bit "IN_SELECTEDQ" {
              position 29;
            }
            ext:bit "EXITIF_ERROR" {
              position 30;
            }
            ext:bit "GROUP_HEAD" {
              position 31;
            }
        }
        leaf imTableId {
          type uint32 {
            range "0..4294967295";
          }
          config false;
          description
            "ID of the routing table to which routes are imported.";
        }
        leaf nexthop {
          type inet:ip-address-no-zone;
          config false;
          description
            "Next hop address to which packets are forwarded.";
        }
        leaf locPrf {
          type uint32 {
            range "0..4294967295";
          }
          config false;
          description
            "Local-preference.";
        }
        leaf prefVal {
          type uint32 {
            range "0..4294967295";
          }
          config false;
          description
            "Preferred value of a protocol.";
        }
        leaf prefrence {
          type uint8 {
            range "0..255";
          }
          config false;
          description
            "Priority of BGP routes.";
        }
        leaf pathAs {
          type string {
            length "0..300";
          }
          config false;
          description
            "List of the AS_Paths that packets pass through.";
        }
        leaf origin {
          type bgpcommOrigin;
          config false;
          description
            "Route origin.";
        }
        leaf med {
          type uint32 {
            range "0..4294967295";
          }
          config false;
          description
            "Route MED.";
        }
        leaf flagString {
          type string {
            length "0..100";
          }
          config false;
          description
            "Route flag that contains a string of characters.";
        }
        leaf rd {
          type string {
            length "0..22";
          }
          config false;
          description
            "Route distinguisher.";
        }
        leaf rtWorseReson {
          type string {
            length "1..50";
          }
          config false;
          description
            "Reason why a route is not selected.";
        }
        leaf peerString {
          type string {
            length "0..300";
          }
          config false;
          description
            "List of route sending peers.";
        }
        leaf time {
          type uint32 {
            range "0..4294967295";
          }
          config false;
          description
            "Time stamp of a route.";
        }
        leaf community {
          type string {
            length "0..120";
          }
          config false;
          description
            "Community attribute.";
        }
        leaf extCommunity {
          type string {
            length "0..300";
          }
          config false;
          description
            "Extended community attribute.";
        }
        leaf from {
          type inet:ip-address-no-zone;
          config false;
          description
            "Source peer that sends a route.";
        }
        leaf ifName {
          type pub-type:ifName;
          config false;
          description
            "Name of the outbound interface of a route.";
        }
        leaf originator {
          type inet:ip-address-no-zone;
          config false;
          description
            "Router ID of the route initiator.";
        }
        leaf clusterList {
          type string {
            length "0..300";
          }
          config false;
          description
            "List of cluster IDs.";
        }
        leaf remoteRouteId {
          type inet:ipv4-address-no-zone;
          config false;
          description
            "Router ID of a peer.";
        }
        leaf relayNexthop {
          type inet:ip-address-no-zone;
          config false;
          description
            "Next hop to which a route is iterated.";
        }
        leaf relaytnlName {
          type string {
            length "0..64";
          }
          config false;
          description
            "Name of a tunnel to which a route is iterated.";
        }
        leaf isAtomicAggre {
          type boolean;
          default "false";
          config false;
          description
            "Route carrying the atomic-aggregate attribute.";
        }
        leaf aggregatorAs {
          type string {
            length "1..11";
          }
          config false;
          description
            "AS number of the route summarizer.";
        }
        leaf aggregatorId {
          type inet:ip-address-no-zone;
          config false;
          description
            "ID of the route summarizer.";
        }
        leaf inLabel {
          type uint32 {
            range "0..4294967295";
          }
          config false;
          description
            "In-label.";
        }
        leaf outLabel {
          type uint32 {
            range "0..4294967295";
          }
          config false;
          description
            "Out-label.";
        }
        leaf pathID {
          type string {
            length "0..50";
          }
          config false;
          description
            "Path ID.";
        }
        leaf vrfName {
          type string {
            length "0..31";
          }
          config false;
          description
            "Iterated Vrf .";
        }
        leaf remoteNextHopTunnelAddress {
          type inet:ip-address-no-zone;
          config false;
          description
            "The remote next hop tunnel adress.";
        }
        leaf remoteNextHopVni {
          type uint32 {
            range "0..4294967295";
          }
          config false;
          description
            "The remote next hop vni.";
        }
        leaf remoteNextHopMacAdress {
          type pub-type:macAddress {
            length "0..60";
          }
          config false;
          description
            "The Remote next hop mac.";
        }
      }
    }
    container bgpLsp {
      description
        "BGP LSP configuration and query items.";
      container bgpLspBfd {
        description
          "The information of dynamic BFD for BGP LSP.";
        container bgpLspBfdParameter {
          description
            "Parameters of BFD for BGP LSP.";
          leaf bgpBfdEnable {
            type boolean;
            default "false";
            description
              "Enable dynamic BFD for BGP LSP.";
          }
          leaf bgpBfdMinTx {
            type uint32 {
              range "3..1000";
            }
            units ms;
            description
              "Interval at which BFD packets are sent. The value ranges from 3 to 1000, in milliseconds.";
            ext:allowDelete "true";
          }
          leaf bgpBfdMinRx {
            type uint32 {
              range "3..1000";
            }
            units ms;
            description
              "Interval at which BFD packets are received. The value ranges from 3 to 1000, in milliseconds.";
            ext:allowDelete "true";
          }
          leaf bgpBfdDetectMultiplier {
            type uint32 {
              range "3..50";
            }
            default "3";
            description
              "BFD detection multiplier. The value ranges from 3 to 50. The default value is 3.";
          }
          leaf bgpBfdTrigger {
            type bgpBfdTriggerType;
            default "none";
            description
              "Configure a policy for creating BGP LSP BFD sessions.";
          }
          leaf bgpBfdTriggerIpPrefix {
            when "not(../bgpBfdTrigger!='ip-prefix')";
            type ipPrefix {
              length "1..169";
              pattern '([^\? ]+)';
            }
            description
              "To use an IP prefix list to dynamically create BFD sessions, specify a name of the IP prefix list.";
            ext:allowDelete "true";
          }
        }
        container bgpLspBfdSessions {
          config false;
          description
            "Display all the sessions of dynamic BFD for BGP LSP.";
          list bgpLspBfdSession {
            key "fecAddress outIfName nextHop";
            config false;
            description
              "Display a session of dynamic BFD for BGP LSP.";
            leaf fecAddress {
              type inet:ipv4-address-no-zone;
              config false;
              description
                "Display the FEC address of the session of dynamic BFD for BGP LSP.";
            }
            leaf outIfName {
              type pub-type:ifName;
              config false;
              description
                "Display the outbound interface of a BGP LSP.";
            }
            leaf nextHop {
              type inet:ipv4-address-no-zone;
              config false;
              description
                "Display the next hop of a BGP LSP.";
            }
            leaf lspIndex {
              type uint32;
              config false;
              description
                "Display the LSP index of a BGP LSP.";
            }
            leaf bfdDiscriminator {
              type uint32;
              config false;
              description
                "Display the BFD discriminator of the BFD session of dynamic BFD for BGP LSP.";
            }
            leaf sessionState {
              type bgpLspBfdSessionState;
              config false;
              description
                "Display the BFD session state of dynamic BFD for BGP LSP.";
            }
            leaf minTxInt {
              type uint32;
              config false;
              description
                "Display the minimum interval at which BFD packets of the session of dynamic BFD for BGP LSP are sent. The value is expressed in milliseconds.";
            }
            leaf minRxInt {
              type uint32;
              config false;
              description
                "Display the minimum interval at which BFD packets of the session of dynamic BFD for BGP LSP are received. The value is expressed in milliseconds.";
            }
            leaf detectMulti {
              type uint32;
              config false;
              description
                "Display the BFD detection multiplier of the BFD session of dynamic BFD for BGP LSP.";
            }
            leaf sessionAge {
              type uint32;
              config false;
              description
                "Display the BFD session age of dynamic BFD for BGP LSP.";
            }
          }
        }
      }
      container bgpLspInfos {
        config false;
        description
          "List of BGP LSPs.";
        list bgpLspInfo {
          key "vrfName afType lspAddr prefixLength lspIndex lspType indirectID frrType";
          config false;
          description
            "BGP LSP.";
          leaf vrfName {
            type string {
              length "0..32";
            }
            config false;
            description
              "Name of a BGP instance.";
          }
          leaf vrfRD {
            type string {
              length "3..21";
            }
            config false;
            description
              "A VPN address family takes effect only after it is configured with an RD. The format of an RD is as follows:
1. 16-bit AS number:32-bit user-defined number, for example, 101:3. An AS number ranges from 0 to 65535, and a user-defined number ranges from 0 to 4294967295. The AS number and user-defined number cannot be both 0s. This means that the RD value cannot be 0:0.
2. 32-bit IP address:16-bit user-defined number, for example: 192.168.122.15:1. The IP address ranges from 0.0.0.0 to 255.255.255.255, and the user-defined number ranges from 0 to 65535.
3. 32-bit AS number:16-bit user-defined number, for example, 10.11:3. An AS number ranges from 0.0 to 65535.65535 or from 0 to 4294967295, and a user-defined number ranges from 0 to 65535. The AS number and user-defined number cannot be both 0s. This means that the RD value cannot be 0.0:0.";
          }
          leaf afType {
            type bgpcommPrefixType;
            config false;
            description
              "Specifies the address family type of a BGP instance. ";
          }
          leaf lspAddr {
            type inet:ip-address-no-zone;
            config false;
            description
              "Destination address of an LSP.";
          }
          leaf prefixLength {
            type uint32 {
              range "0..128";
            }
            config false;
            description
              "Prefix length of the destination address of an LSP.";
          }
          leaf lspIndex {
            type uint32;
            config false;
            description
              "LSP index.";
          }
          leaf lspType {
            type bgpLspType;
            config false;
            description
              "LSP type.";
          }
          leaf inIfaceName {
            type pub-type:ifName;
            config false;
            description
              "Inbound interface of an LSP.";
          }
          leaf outIfaceName {
            type pub-type:ifName;
            config false;
            description
              "Outbound interface of an LSP.";
          }
          leaf indirectID {
            type string {
              length "1..50";
            }
            config false;
            description
              "IndirectID.";
          }
          leaf nextHop {
            type inet:ip-address-no-zone;
            config false;
            description
              "Next hop of an LSP.";
          }
          leaf frrType {
            type bgpLspFrrType;
            config false;
            description
              "FRR role.";
          }
          leaf lspMtu {
            type uint32 {
              range "0..65535";
            }
            config false;
            description
              "LSP MTU.";
          }
          leaf lspTimeStamp {
            type uint32 {
              range "0..4294967295";
            }
            config false;
            description
              "LSP duration.";
          }
          leaf inLabel {
            type uint32 {
              range "0..4294967295";
            }
            config false;
            description
              "In-label of an LSP.";
          }
          leaf outLabel {
            type uint32 {
              range "0..4294967295";
            }
            config false;
            description
              "Out-label of an LSP.";
          }
          leaf outGoingTunnelId {
            type string {
              length "1..50";
            }
            config false;
            description
              "Index of an outbound LSP.";
          }
          leaf labelOperationType {
            type bgpLabelOperationType;
            config false;
            description
              "Label operation type.";
          }
          leaf expMode {
            type bgpcommExpModeType;
            config false;
            description
              "QoS Priority Mode of an LSP.";
          }
          leaf tunnelID {
            type string {
              length "1..50";
            }
            config false;
            description
              "ID of an Outbound LSP";
          }
        }
      }
    }
    container bgpEvrfs {
      config false;
      description
        "EVPN private instance list.";
      list bgpEvrf {
        key "vrfName";
        config false;
        max-elements  "4096";
        description
          "EVPN private instance.";
        leaf vrfName {
          type string {
            length "1..31";
          }
          config false;
          description
            "Name of an EVPN instance.";
        }
        container interfaceEsiInfos {
          config false;
          description
            "ESI list.";
          list interfaceEsiInfo {
            key "effectEsi";
            config false;
            description
              "ESI.";
            leaf effectEsi {
              type string {
                length "0..60";
              }
              config false;
              description
                "Effective ESI.";
            }
            leaf dyminalEsi {
              type string {
                length "0..60";
              }
              config false;
              description
                "Dynamic ESI.";
            }
            leaf staticEsi {
              type string {
                length "0..60";
              }
              config false;
              description
                "Static ESI.";
            }
            container ifLists {
              config false;
              description
                "Interface information list.";
              list ifList {
                key "ifName";
                config false;
                description
                  "Interface information.";
                leaf ifName {
                  type pub-type:ifName;
                  config false;
                  description
                    "Interface Name.";
                }
              }
            }
          }
        }
        container dfTimerInfos {
          config false;
          description
            "DF timer list.";
          list dfTimerInfo {
            key "esi";
            config false;
            description
              "DF timer.";
            leaf esi {
              type string {
                length "0..60";
              }
              config false;
              description
                "Effective ESI.";
            }
            leaf ifName {
              type pub-type:ifName;
              config false;
              description
                "Interface Name.";
            }
            leaf timerType {
              type dfTimerType;
              config false;
              description
                "DF election timer type.";
            }
            leaf timerMode {
              type dfTimerMode;
              config false;
              description
                "DF election timer mode.";
            }
            leaf timerLeftTime {
              type uint32;
              config false;
              description
                "Time to elapse before a DF election timer expires, expressed in seconds.";
            }
          }
        }
        container dfResults {
          config false;
          description
            "DF election result list.";
          list dfResult {
            key "esi ifName";
            config false;
            description
              "DF election result.";
            leaf esi {
              type string {
                length "0..60";
              }
              config false;
              description
                "Effective ESI.";
            }
            leaf ifName {
              type pub-type:ifName;
              config false;
              description
                "Interface Name.";
            }
            leaf dfResult {
              type dfResultType;
              config false;
              description
                "DF election result.";
            }
          }
        }
        container ipPrefixRoutingTables {
          config false;
          description
            "List of Prefix routes in the EVPN address family.";
          list ipPrefixRoutingTable {
            key "rd ipPrefix routeTypeFlag";
            config false;
            description
              "Prefix route.";
            leaf rd {
              type string {
                length "0..60";
              }
              config false;
              description
                "Route distinguisher. An RD is in the format of 32-bit IP address:16-bit user-defined number, for example, 192.168.122.15:1. The IP address ranges from 0.0.0.0 to 255.255.255.255, and the user-defined number ranges from 0 to 65536. An EVN address family takes effect only after it is configured with a RD.";
            }
            leaf ipPrefix {
              type string {
                length "0..60";
              }
              config false;
              description
                "Prefix route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "0..300";
              }
              config false;
              description
                "List of the ASs that packets pass through.";
            }
            leaf origin {
              type bgpcommOrigin;
              config false;
              description
                "Origin of a route.";
            }
            leaf med {
              type uint32 {
                range "0..4294967295";
              }
              config false;
              description
                "Route MED.";
            }
            leaf flagString {
              type string {
                length "0..100";
              }
              config false;
              description
                "Route flag in the format of a character string.";
            }
            leaf peerString {
              type string {
                length "0..300";
              }
              config false;
              description
                "List of sending peers.";
            }
            leaf time {
              type uint32 {
                range "0..4294967295";
              }
              config false;
              description
                "Time stamp of a route.";
            }
            leaf extCommunity {
              type string {
                length "0..300";
              }
              config false;
              description
                "Extended community attribute.";
            }
            leaf rtWorseReson {
              type string {
                length "1..50";
              }
              config false;
              description
                "Reason why a route is not selected.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "0..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "0..300";
              }
              config false;
              description
                "PMSI attribute.";
            }
            leaf mplsLabel1 {
              type uint32 {
                range "0..4294967295";
              }
              config false;
              description
                "Label1,it means L2 VNI for MAC Route and L3 VNI for Prefix Route.";
            }
            leaf mplsLabel2 {
              type uint32 {
                range "0..4294967295";
              }
              config false;
              description
                "Label2,it means L3 VNI for MAC Route.";
            }
            leaf attrString {
              type string {
                length "0..300";
              }
              config false;
              description
                "Other attribute.";
            }
            leaf community {
              type string {
                length "0..120";
              }
              config false;
              description
                "Community attribute.";
            }
            leaf clusterList {
              type string {
                length "0..300";
              }
              config false;
              description
                "List of cluster IDs.";
            }
          }
        }
        container macRoutingTables {
          config false;
          description
            "List of MAC routes in the EVPN address family.";
          list macRoutingTable {
            key "rd macPrefix routeTypeFlag";
            config false;
            description
              "MAC route.";
            leaf rd {
              type string {
                length "0..60";
              }
              config false;
              description
                "Route distinguisher. An RD is in the format of 32-bit IP address:16-bit user-defined number, for example, 192.168.122.15:1. The IP address ranges from 0.0.0.0 to 255.255.255.255, and the user-defined number ranges from 0 to 65536. An EVN address family takes effect only after it is configured with a RD.";
            }
            leaf macPrefix {
              type string {
                length "0..60";
              }
              config false;
              description
                "MAC route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf sourceAFI {
              type bgpcommPrefixType;
              config false;
              description
                "Source address Family.";
            }
            leaf sourceRD {
              type string {
                length "3..21";
              }
              config false;
              description
                "Source RD.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "0..300";
              }
              config false;
              description
                "List of the ASs that packets pass through.";
            }
            leaf origin {
              type bgpcommOrigin;
              config false;
              description
                "Origin of a route.";
            }
            leaf med {
              type uint32 {
                range "0..4294967295";
              }
              config false;
              description
                "Route MED.";
            }
            leaf flagString {
              type string {
                length "0..100";
              }
              config false;
              description
                "Route flag in the format of a character string.";
            }
            leaf peerString {
              type string {
                length "0..300";
              }
              config false;
              description
                "List of sending peers.";
            }
            leaf time {
              type uint32 {
                range "0..4294967295";
              }
              config false;
              description
                "Time stamp of a route.";
            }
            leaf extCommunity {
              type string {
                length "0..300";
              }
              config false;
              description
                "Extended community attribute.";
            }
            leaf rtWorseReson {
              type string {
                length "1..50";
              }
              config false;
              description
                "Reason why a route is not selected.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "0..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "0..300";
              }
              config false;
              description
                "PMSI attribute.";
            }
            leaf mplsLabel1 {
              type uint32 {
                range "0..4294967295";
              }
              config false;
              description
                "Label1,it means L2 VNI for MAC Route and L3 VNI for Prefix Route.";
            }
            leaf mplsLabel2 {
              type uint32 {
                range "0..4294967295";
              }
              config false;
              description
                "Label2,it means L3 VNI for MAC Route.";
            }
            leaf attrString {
              type string {
                length "0..300";
              }
              config false;
              description
                "Other attribute.";
            }
            leaf community {
              type string {
                length "0..120";
              }
              config false;
              description
                "Community attribute.";
            }
            leaf clusterList {
              type string {
                length "0..300";
              }
              config false;
              description
                "List of cluster IDs.";
            }
          }
        }
        container esRoutingTables {
          config false;
          description
            "List of ES routes in the EVN address family.";
          list esRoutingTable {
            key "rd esPrefix routeTypeFlag";
            config false;
            description
              "ES route in the EVN address family.";
            leaf rd {
              type string {
                length "0..60";
              }
              config false;
              description
                "Route distinguisher. An RD is in the format of 32-bit IP address:16-bit user-defined number, for example, 192.168.122.15:1. The IP address ranges from 0.0.0.0 to 255.255.255.255, and the user-defined number ranges from 0 to 65536. An EVN address family takes effect only after it is configured with a RD.";
            }
            leaf esPrefix {
              type string {
                length "0..60";
              }
              config false;
              description
                "ES route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Rreference of a route.";
            }
            leaf pathAs {
              type string {
                length "0..300";
              }
              config false;
              description
                "List of the ASs that packets pass through.";
            }
            leaf origin {
              type bgpcommOrigin;
              config false;
              description
                "Origin of a route.";
            }
            leaf med {
              type uint32 {
                range "0..4294967295";
              }
              config false;
              description
                "Route MED.";
            }
            leaf flagString {
              type string {
                length "0..100";
              }
              config false;
              description
                "Route flag that contains a string of characters.";
            }
            leaf rtWorseReson {
              type string {
                length "1..50";
              }
              config false;
              description
                "Reason why a route is not selected.";
            }
            leaf peerString {
              type string {
                length "0..300";
              }
              config false;
              description
                "List of sending peers.";
            }
            leaf time {
              type uint32 {
                range "0..4294967295";
              }
              config false;
              description
                "Time stamp of a route.";
            }
            leaf extCommunity {
              type string {
                length "0..300";
              }
              config false;
              description
                "Extended community attribute.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "0..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "0..300";
              }
              config false;
              description
                "PMSI attribute.";
            }
            leaf attrString {
              type string {
                length "0..300";
              }
              config false;
              description
                "Other attribute.";
            }
            leaf community {
              type string {
                length "0..120";
              }
              config false;
              description
                "Community attribute.";
            }
            leaf clusterList {
              type string {
                length "0..300";
              }
              config false;
              description
                "List of cluster IDs.";
            }
          }
        }
        container multiRoutingTables {
          config false;
          description
            "List of inclusive routes information in the EVPN address family.";
          list multiRoutingTable {
            key "rd inclusivePrefix routeTypeFlag";
            config false;
            description
              "Inclusive route in the EVPN address family.";
            leaf rd {
              type string {
                length "0..60";
              }
              config false;
              description
                "Route distinguisher. An EVN address family takes effect only after it is configured with a RD. The format of an RD is as follows:32-bit IP address:16-bit user-defined number, for example: 192.168.122.15:1.The IP address ranges from 0.0.0.0 to 255.255.255.255, and the user-defined number ranges from 0 to 65536.";
            }
            leaf inclusivePrefix {
              type inet:ipv4-address-no-zone;
              config false;
              description
                "Inclusive route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "0..300";
              }
              config false;
              description
                "List of the ASs that packets pass through.";
            }
            leaf origin {
              type bgpcommOrigin;
              config false;
              description
                "Origin of a route.";
            }
            leaf med {
              type uint32 {
                range "0..4294967295";
              }
              config false;
              description
                "Route MED in the attribute node.";
            }
            leaf flagString {
              type string {
                length "0..100";
              }
              config false;
              description
                "Route flag in the format of a character string.";
            }
            leaf rtWorseReson {
              type string {
                length "1..50";
              }
              config false;
              description
                "Reason why a route is not selected.";
            }
            leaf peerString {
              type string {
                length "0..300";
              }
              config false;
              description
                "List of sending peers.";
            }
            leaf time {
              type uint32 {
                range "0..4294967295";
              }
              config false;
              description
                "Time stamp of a route.";
            }
            leaf extCommunity {
              type string {
                length "0..300";
              }
              config false;
              description
                "Extended community attribute.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "0..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "0..300";
              }
              config false;
              description
                "PMSI attribute.";
            }
            leaf attrString {
              type string {
                length "0..300";
              }
              config false;
              description
                "Other attribute.";
            }
            leaf community {
              type string {
                length "0..120";
              }
              config false;
              description
                "Community attribute.";
            }
            leaf clusterList {
              type string {
                length "0..300";
              }
              config false;
              description
                "List of cluster IDs.";
            }
          }
        }
        container adRoutingTables {
          config false;
          description
            "Information about AD routes in the EVPN address family.";
          list adRoutingTable {
            key "rd adPrefix routeTypeFlag";
            config false;
            description
              "Information about AD routes in the EVPN address family.";
            leaf rd {
              type string {
                length "0..60";
              }
              config false;
              description
                "Route distinguisher. An RD is in the format of 32-bit IP address:16-bit user-defined number, for example, 192.168.122.15:1. The IP address ranges from 0.0.0.0 to 255.255.255.255, and the user-defined number ranges from 0 to 65536. An EVN address family takes effect only after it is configured with a RD.";
            }
            leaf adPrefix {
              type string {
                length "0..60";
              }
              config false;
              description
                "AD route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "0..300";
              }
              config false;
              description
                "List of the ASs that packets pass through.";
            }
            leaf origin {
              type bgpcommOrigin;
              config false;
              description
                "Origin of a route.";
            }
            leaf med {
              type uint32 {
                range "0..4294967295";
              }
              config false;
              description
                "Route MED in the attribute node.";
            }
            leaf flagString {
              type string {
                length "0..100";
              }
              config false;
              description
                "Route flag that contains a string of characters.";
            }
            leaf rtWorseReson {
              type string {
                length "1..50";
              }
              config false;
              description
                "Reason why a route is not selected.";
            }
            leaf peerString {
              type string {
                length "0..300";
              }
              config false;
              description
                "List of sending peers.";
            }
            leaf time {
              type uint32 {
                range "0..4294967295";
              }
              config false;
              description
                "Time stamp of a route.";
            }
            leaf extCommunity {
              type string {
                length "0..300";
              }
              config false;
              description
                "Extended community attribute.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "0..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "0..300";
              }
              config false;
              description
                "PMSI attribute.";
            }
            leaf attrString {
              type string {
                length "0..300";
              }
              config false;
              description
                "Other attribute.";
            }
            leaf community {
              type string {
                length "0..120";
              }
              config false;
              description
                "Community attribute.";
            }
            leaf clusterList {
              type string {
                length "0..300";
              }
              config false;
              description
                "List of cluster IDs.";
            }
          }
        }
      }
    }
    container bgpInsts {
      config false;
      description
        "Index Name List of BGP instance.";
      list bgpInst {
        key "bgpName";
        config false;
        max-elements  "32";
        description
          "Index Name of a BGP instance.";
        leaf bgpName {
          type string {
            length "0..31";
          }
          config false;
          description
            "Name of a BGP instance.";
        }
      }
    }
  }
  grouping bgp_evpnMacRoutingTables_type {
    description
      "";
    list macRoutingTable {
      key "rd macPrefix routeTypeFlag";
      config false;
      description
        "MAC route.";
      leaf rd {
        type string {
          length "0..60";
        }
        config false;
        description
          "Route distinguisher. An RD is in the format of 32-bit IP address:16-bit user-defined number, for example, 192.168.122.15:1. The IP address ranges from 0.0.0.0 to 255.255.255.255, and the user-defined number ranges from 0 to 65536. An EVN address family takes effect only after it is configured with a RD.";
      }
      leaf macPrefix {
        type string {
          length "0..60";
        }
        config false;
        description
          "MAC route prefix.";
      }
      leaf routeTypeFlag {
        type pub-type:bits32;
        config false;
        description
          "Route type.";
        ext:masklen 32;
          ext:bit "ibgp" {
            position 0;
          }
          ext:bit "ebgp" {
            position 1;
          }
          ext:bit "network" {
            position 2;
          }
          ext:bit "import" {
            position 3;
          }
          ext:bit "auto-summary" {
            position 4;
          }
          ext:bit "aggregate" {
            position 5;
          }
          ext:bit "cpri" {
            position 6;
          }
          ext:bit "pcri" {
            position 7;
          }
          ext:bit "suppressed" {
            position 8;
          }
          ext:bit "NHP-EMPTY" {
            position 9;
          }
          ext:bit "NO-ADV" {
            position 10;
          }
          ext:bit "local_cross" {
            position 11;
          }
          ext:bit "remote_cross" {
            position 12;
          }
          ext:bit "VD-BGP" {
            position 13;
          }
          ext:bit "PATH_LOCAL" {
            position 14;
          }
          ext:bit "PATH_GATEWAY" {
            position 15;
          }
          ext:bit "policy_nopass" {
            position 16;
          }
          ext:bit "supprenet" {
            position 17;
          }
          ext:bit "dampened" {
            position 18;
          }
          ext:bit "history" {
            position 19;
          }
          ext:bit "select" {
            position 20;
          }
          ext:bit "best" {
            position 21;
          }
          ext:bit "backup" {
            position 22;
          }
          ext:bit "attr_change" {
            position 23;
          }
          ext:bit "NHLFE_CREATED" {
            position 24;
          }
          ext:bit "ILM_CREATED" {
            position 25;
          }
          ext:bit "NEXTHOP_CHANGE" {
            position 26;
          }
          ext:bit "Invaild" {
            position 27;
          }
          ext:bit "SOURCE_CHANGE" {
            position 28;
          }
          ext:bit "IN_SELECTEDQ" {
            position 29;
          }
          ext:bit "EXITIF_ERROR" {
            position 30;
          }
          ext:bit "GROUP_HEAD" {
            position 31;
          }
      }
      leaf nexthop {
        type inet:ip-address-no-zone;
        config false;
        description
          "Next-hop address to which packets are sent.";
      }
      leaf locPrf {
        type uint32 {
          range "0..4294967295";
        }
        config false;
        description
          "Local priority.";
      }
      leaf sourceAFI {
        type bgpcommPrefixType;
        config false;
        description
          "Source address Family.";
      }
      leaf sourceRD {
        type string {
          length "3..21";
        }
        config false;
        description
          "Source RD.";
      }
      leaf prefVal {
        type uint32 {
          range "0..4294967295";
        }
        config false;
        description
          "Preferred value of a protocol.";
      }
      leaf prefrence {
        type uint8 {
          range "0..255";
        }
        config false;
        description
          "Preference of a route.";
      }
      leaf pathAs {
        type string {
          length "0..300";
        }
        config false;
        description
          "List of the ASs that packets pass through.";
      }
      leaf origin {
        type bgpcommOrigin;
        config false;
        description
          "Origin of a route.";
      }
      leaf med {
        type uint32 {
          range "0..4294967295";
        }
        config false;
        description
          "Route MED.";
      }
      leaf flagString {
        type string {
          length "0..100";
        }
        config false;
        description
          "Route flag in the format of a character string.";
      }
      leaf peerString {
        type string {
          length "0..300";
        }
        config false;
        description
          "List of sending peers.";
      }
      leaf time {
        type uint32 {
          range "0..4294967295";
        }
        config false;
        description
          "Time stamp of a route.";
      }
      leaf extCommunity {
        type string {
          length "0..300";
        }
        config false;
        description
          "Extended community attribute.";
      }
      leaf rtWorseReson {
        type string {
          length "1..50";
        }
        config false;
        description
          "Reason why a route is not selected.";
      }
      leaf from {
        type inet:ip-address-no-zone;
        config false;
        description
          "Source peer that sends a route.";
      }
      leaf ifName {
        type string {
          length "1..63";
        }
        config false;
        description
          "Name of the outbound interface of a route.";
      }
      leaf originator {
        type inet:ipv4-address-no-zone;
        config false;
        description
          "Router ID of the route initiator.";
      }
      leaf remoteRouteId {
        type inet:ipv4-address-no-zone;
        config false;
        description
          "Router ID of a peer.";
      }
      leaf relayNexthop {
        type inet:ip-address-no-zone;
        config false;
        description
          "Iterated next hop.";
      }
      leaf relaytnlName {
        type string {
          length "0..64";
        }
        config false;
        description
          "Name of an iteration tunnel.";
      }
      leaf inLabel {
        type uint32 {
          range "0..4294967295";
        }
        config false;
        description
          "In-label.";
      }
      leaf outLabel {
        type uint32 {
          range "0..4294967295";
        }
        config false;
        description
          "Out-label.";
      }
      leaf pmsiString {
        type string {
          length "0..300";
        }
        config false;
        description
          "PMSI attribute.";
      }
      leaf mplsLabel1 {
        type uint32 {
          range "0..4294967295";
        }
        config false;
        description
          "Label1,it means L2 VNI for MAC Route and L3 VNI for Prefix Route.";
      }
      leaf mplsLabel2 {
        type uint32 {
          range "0..4294967295";
        }
        config false;
        description
          "Label2,it means L3 VNI for MAC Route.";
      }
      leaf attrString {
        type string {
          length "0..300";
        }
        config false;
        description
          "Other attribute.";
      }
      leaf community {
        type string {
          length "0..120";
        }
        config false;
        description
          "Community attribute.";
      }
      leaf clusterList {
        type string {
          length "0..300";
        }
        config false;
        description
          "List of cluster IDs.";
      }
    }
  }
  grouping bgp_evpnEsRoutingTables_type {
    description
      "";
    list esRoutingTable {
      key "rd esPrefix routeTypeFlag";
      config false;
      description
        "ES route in the EVN address family.";
      leaf rd {
        type string {
          length "0..60";
        }
        config false;
        description
          "Route distinguisher. An RD is in the format of 32-bit IP address:16-bit user-defined number, for example, 192.168.122.15:1. The IP address ranges from 0.0.0.0 to 255.255.255.255, and the user-defined number ranges from 0 to 65536. An EVN address family takes effect only after it is configured with a RD.";
      }
      leaf esPrefix {
        type string {
          length "0..60";
        }
        config false;
        description
          "ES route prefix.";
      }
      leaf routeTypeFlag {
        type pub-type:bits32;
        config false;
        description
          "Route type.";
        ext:masklen 32;
          ext:bit "ibgp" {
            position 0;
          }
          ext:bit "ebgp" {
            position 1;
          }
          ext:bit "network" {
            position 2;
          }
          ext:bit "import" {
            position 3;
          }
          ext:bit "auto-summary" {
            position 4;
          }
          ext:bit "aggregate" {
            position 5;
          }
          ext:bit "cpri" {
            position 6;
          }
          ext:bit "pcri" {
            position 7;
          }
          ext:bit "suppressed" {
            position 8;
          }
          ext:bit "NHP-EMPTY" {
            position 9;
          }
          ext:bit "NO-ADV" {
            position 10;
          }
          ext:bit "local_cross" {
            position 11;
          }
          ext:bit "remote_cross" {
            position 12;
          }
          ext:bit "VD-BGP" {
            position 13;
          }
          ext:bit "PATH_LOCAL" {
            position 14;
          }
          ext:bit "PATH_GATEWAY" {
            position 15;
          }
          ext:bit "policy_nopass" {
            position 16;
          }
          ext:bit "supprenet" {
            position 17;
          }
          ext:bit "dampened" {
            position 18;
          }
          ext:bit "history" {
            position 19;
          }
          ext:bit "select" {
            position 20;
          }
          ext:bit "best" {
            position 21;
          }
          ext:bit "backup" {
            position 22;
          }
          ext:bit "attr_change" {
            position 23;
          }
          ext:bit "NHLFE_CREATED" {
            position 24;
          }
          ext:bit "ILM_CREATED" {
            position 25;
          }
          ext:bit "NEXTHOP_CHANGE" {
            position 26;
          }
          ext:bit "Invaild" {
            position 27;
          }
          ext:bit "SOURCE_CHANGE" {
            position 28;
          }
          ext:bit "IN_SELECTEDQ" {
            position 29;
          }
          ext:bit "EXITIF_ERROR" {
            position 30;
          }
          ext:bit "GROUP_HEAD" {
            position 31;
          }
      }
      leaf nexthop {
        type inet:ip-address-no-zone;
        config false;
        description
          "Next-hop address to which packets are sent.";
      }
      leaf locPrf {
        type uint32 {
          range "0..4294967295";
        }
        config false;
        description
          "Local priority.";
      }
      leaf prefVal {
        type uint32 {
          range "0..4294967295";
        }
        config false;
        description
          "Preferred value of a protocol.";
      }
      leaf prefrence {
        type uint8 {
          range "0..255";
        }
        config false;
        description
          "Rreference of a route.";
      }
      leaf pathAs {
        type string {
          length "0..300";
        }
        config false;
        description
          "List of the ASs that packets pass through.";
      }
      leaf origin {
        type bgpcommOrigin;
        config false;
        description
          "Origin of a route.";
      }
      leaf med {
        type uint32 {
          range "0..4294967295";
        }
        config false;
        description
          "Route MED.";
      }
      leaf flagString {
        type string {
          length "0..100";
        }
        config false;
        description
          "Route flag that contains a string of characters.";
      }
      leaf rtWorseReson {
        type string {
          length "1..50";
        }
        config false;
        description
          "Reason why a route is not selected.";
      }
      leaf peerString {
        type string {
          length "0..300";
        }
        config false;
        description
          "List of sending peers.";
      }
      leaf time {
        type uint32 {
          range "0..4294967295";
        }
        config false;
        description
          "Time stamp of a route.";
      }
      leaf extCommunity {
        type string {
          length "0..300";
        }
        config false;
        description
          "Extended community attribute.";
      }
      leaf from {
        type inet:ip-address-no-zone;
        config false;
        description
          "Source peer that sends a route.";
      }
      leaf ifName {
        type string {
          length "1..63";
        }
        config false;
        description
          "Name of the outbound interface of a route.";
      }
      leaf originator {
        type inet:ipv4-address-no-zone;
        config false;
        description
          "Router ID of the route initiator.";
      }
      leaf remoteRouteId {
        type inet:ipv4-address-no-zone;
        config false;
        description
          "Router ID of a peer.";
      }
      leaf relayNexthop {
        type inet:ip-address-no-zone;
        config false;
        description
          "Iterated next hop.";
      }
      leaf relaytnlName {
        type string {
          length "0..64";
        }
        config false;
        description
          "Name of an iteration tunnel.";
      }
      leaf inLabel {
        type uint32 {
          range "0..4294967295";
        }
        config false;
        description
          "In-label.";
      }
      leaf outLabel {
        type uint32 {
          range "0..4294967295";
        }
        config false;
        description
          "Out-label.";
      }
      leaf pmsiString {
        type string {
          length "0..300";
        }
        config false;
        description
          "PMSI attribute.";
      }
      leaf attrString {
        type string {
          length "0..300";
        }
        config false;
        description
          "Other attribute.";
      }
      leaf community {
        type string {
          length "0..120";
        }
        config false;
        description
          "Community attribute.";
      }
      leaf clusterList {
        type string {
          length "0..300";
        }
        config false;
        description
          "List of cluster IDs.";
      }
    }
  }
  grouping bgp_evpnMultiRoutingTables_type {
    description
      "";
    list multiRoutingTable {
      key "rd inclusivePrefix routeTypeFlag";
      config false;
      description
        "Inclusive route in the EVPN address family.";
      leaf rd {
        type string {
          length "0..60";
        }
        config false;
        description
          "Route distinguisher. An EVN address family takes effect only after it is configured with a RD. The format of an RD is as follows:32-bit IP address:16-bit user-defined number, for example: 192.168.122.15:1.The IP address ranges from 0.0.0.0 to 255.255.255.255, and the user-defined number ranges from 0 to 65536.";
      }
      leaf inclusivePrefix {
        type inet:ipv4-address-no-zone;
        config false;
        description
          "Inclusive route prefix.";
      }
      leaf routeTypeFlag {
        type pub-type:bits32;
        config false;
        description
          "Route type.";
        ext:masklen 32;
          ext:bit "ibgp" {
            position 0;
          }
          ext:bit "ebgp" {
            position 1;
          }
          ext:bit "network" {
            position 2;
          }
          ext:bit "import" {
            position 3;
          }
          ext:bit "auto-summary" {
            position 4;
          }
          ext:bit "aggregate" {
            position 5;
          }
          ext:bit "cpri" {
            position 6;
          }
          ext:bit "pcri" {
            position 7;
          }
          ext:bit "suppressed" {
            position 8;
          }
          ext:bit "NHP-EMPTY" {
            position 9;
          }
          ext:bit "NO-ADV" {
            position 10;
          }
          ext:bit "local_cross" {
            position 11;
          }
          ext:bit "remote_cross" {
            position 12;
          }
          ext:bit "VD-BGP" {
            position 13;
          }
          ext:bit "PATH_LOCAL" {
            position 14;
          }
          ext:bit "PATH_GATEWAY" {
            position 15;
          }
          ext:bit "policy_nopass" {
            position 16;
          }
          ext:bit "supprenet" {
            position 17;
          }
          ext:bit "dampened" {
            position 18;
          }
          ext:bit "history" {
            position 19;
          }
          ext:bit "select" {
            position 20;
          }
          ext:bit "best" {
            position 21;
          }
          ext:bit "backup" {
            position 22;
          }
          ext:bit "attr_change" {
            position 23;
          }
          ext:bit "NHLFE_CREATED" {
            position 24;
          }
          ext:bit "ILM_CREATED" {
            position 25;
          }
          ext:bit "NEXTHOP_CHANGE" {
            position 26;
          }
          ext:bit "Invaild" {
            position 27;
          }
          ext:bit "SOURCE_CHANGE" {
            position 28;
          }
          ext:bit "IN_SELECTEDQ" {
            position 29;
          }
          ext:bit "EXITIF_ERROR" {
            position 30;
          }
          ext:bit "GROUP_HEAD" {
            position 31;
          }
      }
      leaf nexthop {
        type inet:ip-address-no-zone;
        config false;
        description
          "Next-hop address to which packets are sent.";
      }
      leaf locPrf {
        type uint32 {
          range "0..4294967295";
        }
        config false;
        description
          "Local priority.";
      }
      leaf prefVal {
        type uint32 {
          range "0..4294967295";
        }
        config false;
        description
          "Preferred value of a protocol.";
      }
      leaf prefrence {
        type uint8 {
          range "0..255";
        }
        config false;
        description
          "Preference of a route.";
      }
      leaf pathAs {
        type string {
          length "0..300";
        }
        config false;
        description
          "List of the ASs that packets pass through.";
      }
      leaf origin {
        type bgpcommOrigin;
        config false;
        description
          "Origin of a route.";
      }
      leaf med {
        type uint32 {
          range "0..4294967295";
        }
        config false;
        description
          "Route MED in the attribute node.";
      }
      leaf flagString {
        type string {
          length "0..100";
        }
        config false;
        description
          "Route flag in the format of a character string.";
      }
      leaf rtWorseReson {
        type string {
          length "1..50";
        }
        config false;
        description
          "Reason why a route is not selected.";
      }
      leaf peerString {
        type string {
          length "0..300";
        }
        config false;
        description
          "List of sending peers.";
      }
      leaf time {
        type uint32 {
          range "0..4294967295";
        }
        config false;
        description
          "Time stamp of a route.";
      }
      leaf extCommunity {
        type string {
          length "0..300";
        }
        config false;
        description
          "Extended community attribute.";
      }
      leaf from {
        type inet:ip-address-no-zone;
        config false;
        description
          "Source peer that sends a route.";
      }
      leaf ifName {
        type string {
          length "1..63";
        }
        config false;
        description
          "Name of the outbound interface of a route.";
      }
      leaf originator {
        type inet:ipv4-address-no-zone;
        config false;
        description
          "Router ID of the route initiator.";
      }
      leaf remoteRouteId {
        type inet:ipv4-address-no-zone;
        config false;
        description
          "Router ID of a peer.";
      }
      leaf relayNexthop {
        type inet:ip-address-no-zone;
        config false;
        description
          "Iterated next hop.";
      }
      leaf relaytnlName {
        type string {
          length "0..64";
        }
        config false;
        description
          "Name of an iteration tunnel.";
      }
      leaf inLabel {
        type uint32 {
          range "0..4294967295";
        }
        config false;
        description
          "In-label.";
      }
      leaf outLabel {
        type uint32 {
          range "0..4294967295";
        }
        config false;
        description
          "Out-label.";
      }
      leaf pmsiString {
        type string {
          length "0..300";
        }
        config false;
        description
          "PMSI attribute.";
      }
      leaf attrString {
        type string {
          length "0..300";
        }
        config false;
        description
          "Other attribute.";
      }
      leaf community {
        type string {
          length "0..120";
        }
        config false;
        description
          "Community attribute.";
      }
      leaf clusterList {
        type string {
          length "0..300";
        }
        config false;
        description
          "List of cluster IDs.";
      }
    }
  }
  grouping bgp_evpnAdRoutingTables_type {
    description
      "";
    list adRoutingTable {
      key "rd adPrefix routeTypeFlag";
      config false;
      description
        "Information about AD routes in the EVPN address family.";
      leaf rd {
        type string {
          length "0..60";
        }
        config false;
        description
          "Route distinguisher. An RD is in the format of 32-bit IP address:16-bit user-defined number, for example, 192.168.122.15:1. The IP address ranges from 0.0.0.0 to 255.255.255.255, and the user-defined number ranges from 0 to 65536. An EVN address family takes effect only after it is configured with a RD.";
      }
      leaf adPrefix {
        type string {
          length "0..60";
        }
        config false;
        description
          "AD route prefix.";
      }
      leaf routeTypeFlag {
        type pub-type:bits32;
        config false;
        description
          "Route type.";
        ext:masklen 32;
          ext:bit "ibgp" {
            position 0;
          }
          ext:bit "ebgp" {
            position 1;
          }
          ext:bit "network" {
            position 2;
          }
          ext:bit "import" {
            position 3;
          }
          ext:bit "auto-summary" {
            position 4;
          }
          ext:bit "aggregate" {
            position 5;
          }
          ext:bit "cpri" {
            position 6;
          }
          ext:bit "pcri" {
            position 7;
          }
          ext:bit "suppressed" {
            position 8;
          }
          ext:bit "NHP-EMPTY" {
            position 9;
          }
          ext:bit "NO-ADV" {
            position 10;
          }
          ext:bit "local_cross" {
            position 11;
          }
          ext:bit "remote_cross" {
            position 12;
          }
          ext:bit "VD-BGP" {
            position 13;
          }
          ext:bit "PATH_LOCAL" {
            position 14;
          }
          ext:bit "PATH_GATEWAY" {
            position 15;
          }
          ext:bit "policy_nopass" {
            position 16;
          }
          ext:bit "supprenet" {
            position 17;
          }
          ext:bit "dampened" {
            position 18;
          }
          ext:bit "history" {
            position 19;
          }
          ext:bit "select" {
            position 20;
          }
          ext:bit "best" {
            position 21;
          }
          ext:bit "backup" {
            position 22;
          }
          ext:bit "attr_change" {
            position 23;
          }
          ext:bit "NHLFE_CREATED" {
            position 24;
          }
          ext:bit "ILM_CREATED" {
            position 25;
          }
          ext:bit "NEXTHOP_CHANGE" {
            position 26;
          }
          ext:bit "Invaild" {
            position 27;
          }
          ext:bit "SOURCE_CHANGE" {
            position 28;
          }
          ext:bit "IN_SELECTEDQ" {
            position 29;
          }
          ext:bit "EXITIF_ERROR" {
            position 30;
          }
          ext:bit "GROUP_HEAD" {
            position 31;
          }
      }
      leaf nexthop {
        type inet:ip-address-no-zone;
        config false;
        description
          "Next-hop address to which packets are sent.";
      }
      leaf locPrf {
        type uint32 {
          range "0..4294967295";
        }
        config false;
        description
          "Local priority.";
      }
      leaf prefVal {
        type uint32 {
          range "0..4294967295";
        }
        config false;
        description
          "Preferred value of a protocol.";
      }
      leaf prefrence {
        type uint8 {
          range "0..255";
        }
        config false;
        description
          "Preference of a route.";
      }
      leaf pathAs {
        type string {
          length "0..300";
        }
        config false;
        description
          "List of the ASs that packets pass through.";
      }
      leaf origin {
        type bgpcommOrigin;
        config false;
        description
          "Origin of a route.";
      }
      leaf med {
        type uint32 {
          range "0..4294967295";
        }
        config false;
        description
          "Route MED in the attribute node.";
      }
      leaf flagString {
        type string {
          length "0..100";
        }
        config false;
        description
          "Route flag that contains a string of characters.";
      }
      leaf rtWorseReson {
        type string {
          length "1..50";
        }
        config false;
        description
          "Reason why a route is not selected.";
      }
      leaf peerString {
        type string {
          length "0..300";
        }
        config false;
        description
          "List of sending peers.";
      }
      leaf time {
        type uint32 {
          range "0..4294967295";
        }
        config false;
        description
          "Time stamp of a route.";
      }
      leaf extCommunity {
        type string {
          length "0..300";
        }
        config false;
        description
          "Extended community attribute.";
      }
      leaf from {
        type inet:ip-address-no-zone;
        config false;
        description
          "Source peer that sends a route.";
      }
      leaf ifName {
        type string {
          length "1..63";
        }
        config false;
        description
          "Name of the outbound interface of a route.";
      }
      leaf originator {
        type inet:ipv4-address-no-zone;
        config false;
        description
          "Router ID of the route initiator.";
      }
      leaf remoteRouteId {
        type inet:ipv4-address-no-zone;
        config false;
        description
          "Router ID of a peer.";
      }
      leaf relayNexthop {
        type inet:ip-address-no-zone;
        config false;
        description
          "Iterated next hop.";
      }
      leaf relaytnlName {
        type string {
          length "0..64";
        }
        config false;
        description
          "Name of an iteration tunnel.";
      }
      leaf inLabel {
        type uint32 {
          range "0..4294967295";
        }
        config false;
        description
          "In-label.";
      }
      leaf outLabel {
        type uint32 {
          range "0..4294967295";
        }
        config false;
        description
          "Out-label.";
      }
      leaf pmsiString {
        type string {
          length "0..300";
        }
        config false;
        description
          "PMSI attribute.";
      }
      leaf attrString {
        type string {
          length "0..300";
        }
        config false;
        description
          "Other attribute.";
      }
      leaf community {
        type string {
          length "0..120";
        }
        config false;
        description
          "Community attribute.";
      }
      leaf clusterList {
        type string {
          length "0..300";
        }
        config false;
        description
          "List of cluster IDs.";
      }
    }
  }
  grouping bgp_evpnInterfaceEsiInfos_type {
    description
      "";
    list interfaceEsiInfo {
      key "effectEsi";
      config false;
      description
        "ESI.";
      leaf effectEsi {
        type string {
          length "0..60";
        }
        config false;
        description
          "Effective ESI.";
      }
      leaf dyminalEsi {
        type string {
          length "0..60";
        }
        config false;
        description
          "Dynamic ESI.";
      }
      leaf staticEsi {
        type string {
          length "0..60";
        }
        config false;
        description
          "Static ESI.";
      }
      container ifLists {
        config false;
        description
          "Interface information list.";
        list ifList {
          key "ifName";
          config false;
          description
            "Interface information.";
          leaf ifName {
            type pub-type:ifName;
            config false;
            description
              "Interface Name.";
          }
        }
      }
    }
  }
  grouping bgp_bgpcomm_evpnAfParameter_type {
    description
      "";
    leaf dfDelayTime {
      type uint32 {
        range "1..1200";
      }
      default "60";
      description
        "Designated forwarder election delay-timer.";
      ext:allowDelete "true";
    }
  }
  grouping bgp_bgpcomm_bgpPeerBfdSessionInfos_type {
    description
      "";
    list bgpPeerBfdSessionInfo {
      key "remoteAddress";
      config false;
      description
        "BFD session.";
      leaf remoteAddress {
        type inet:ip-address-no-zone;
        config false;
        description
          "Peer address of the BFD session.";
      }
      leaf localAdress {
        type inet:ip-address-no-zone;
        config false;
        description
          "Local address of the BFD session.";
      }
      leaf ifName {
        type pub-type:ifName;
        config false;
        description
          "Name of an interface of the BFD session.";
      }
      leaf txInterval {
        type uint32 {
          range "0..4294967295";
        }
        default "0";
        config false;
        description
          "Interval at which BFD packets are sent, in milliseconds.";
      }
      leaf rxInterval {
        type uint32 {
          range "0..4294967295";
        }
        default "0";
        config false;
        description
          "Interval at which BFD packets are received, in milliseconds.";
      }
      leaf multiplier {
        type uint32 {
          range "0..50";
        }
        config false;
        description
          "Detection multiplier. ";
      }
      leaf sessionState {
        type bgpBfdState;
        config false;
        description
          "State of the BFD session.";
      }
      leaf bfdGlobalEnable {
        type boolean;
        config false;
        description
          "Global BFD state.";
      }
    }
  }
  grouping bgp_bgpcomm_peerStatisticsInfo_type {
    description
      "Display the information of the BGP peers";
    leaf recvNLRINum {
      type uint32 {
        range "0..4294967295";
      }
      config false;
      description
        "Number of reachable routes.";
    }
    leaf recvUNLRINum {
      type uint32 {
        range "0..4294967295";
      }
      config false;
      description
        "Number of unreachable routes.";
    }
    leaf prePlyRouteNum {
      type uint32 {
        range "0..4294967295";
      }
      config false;
      description
        "Number of accepted routes.";
    }
    leaf postPlyRouteNum {
      type uint32 {
        range "0..4294967295";
      }
      config false;
      description
        "Number of received routes.";
    }
    leaf bestRouteNum {
      type uint32 {
        range "0..4294967295";
      }
      config false;
      description
        "Number of optimal routes.";
    }
    leaf rejectedRtNum {
      type uint32 {
        range "0..4294967295";
      }
      config false;
      description
        "Number of rejected routes.";
    }
    leaf asPathLoopRtNum {
      type uint32 {
        range "0..4294967295";
      }
      config false;
      description
        "Number of routing loops in an AS.";
    }
    leaf asConfLoopRtNum {
      type uint32 {
        range "0..4294967295";
      }
      config false;
      description
        "Number of routing loops in an AS confederation.";
    }
    leaf cluLoopRtNum {
      type uint32 {
        range "0..4294967295";
      }
      config false;
      description
        "Number of routing loops in a cluster.";
    }
    leaf invalOrigRtNum {
      type uint32 {
        range "0..4294967295";
      }
      config false;
      description
        "Number of routes with an invalid originator ID.";
    }
  }
  grouping bgp_bgpcomm_bgpPeerInfo_type {
    description
      "Display the information of the BGP peers";
    leaf peerType {
      type bgpcommPeerType;
      config false;
      description
        "Configures the type of BGP peers: IBGP or EBGP.";
    }
    leaf version {
      type uint8;
      config false;
      description
        "The current BGP version is BGP-4. BGP-4 provides a set of new mechanisms to support Classless Inter-Domain Routing (CIDR). The new mechanisms also support the network prefix-based advertisement, cancellation of the 'class' concept for a BGP network during the network prefix-supported advertisements, and route summarization and AS path summarization.";
    }
    leaf remoteRouterId {
      type inet:ipv4-address-no-zone;
      config false;
      description
        "Router ID for a peer.";
    }
    leaf bgpCurState {
      type bgpcommPEERSTATE;
      config false;
      description
        "Current BGP state, which can be Idle, Active, Established, Connect, OpenSent, or OpenConfirm.
Idle: In this state, BGP denies all connection requests. This is the initial state of BGP.
Active: In this state, BGP tries to establish TCP connections. This is the intermediate state of BGP.
Established: In this state, BGP peers can exchange Update, Notification, and Keepalive packets with each other.
Connect: In this state, BGP determines the subsequent operation after the TCP connections are established.
OpenSent: In this state, BGP is waiting for the Open packet from the peer.
OpenConfirm: In this state, BGP is waiting for a Notification packet and a Keepalive packet.";
    }
    leaf localPort {
      type uint32;
      config false;
      description
        "Local port number. BGP uses the TCP as the transport layer protocol, and the port number is 179.";
    }
    leaf remotePort {
      type uint32 {
        range "0..4294967295";
      }
      config false;
      description
        "Port number for a peer to establish a peer relationship.";
    }
    leaf currentEvent {
      type string {
        length "0..39";
      }
      config false;
      description
        "Recent event that occurs on a peer.";
    }
    leaf bgpLastState {
      type bgpcommPEERSTATE;
      config false;
      description
        "Last state of a peer, which can be Idle, Connect, Active, OpenSent, OpenConfirm, or Established.";
    }
    leaf upDownDuration {
      type string {
        length "0..49";
      }
      config false;
      description
        "Period during which a BGP session is in the established state.";
    }
    leaf messageSent {
      type uint32 {
        range "0..4294967295";
      }
      config false;
      description
        "Number of packets sent to a peer.";
    }
    leaf messageReceived {
      type uint32 {
        range "0..4294967295";
      }
      config false;
      description
        "Number of packets received from a peer.";
    }
    leaf outQueue {
      type uint32 {
        range "0..4294967295";
      }
      config false;
      description
        "Number of packets to be sent in a queue.";
    }
    leaf revHoldTime {
      type uint32 {
        range "0..65535";
      }
      config false;
      description
        "Hold time of a peer.";
    }
    leaf revLastKeepAliveTime {
      type yang:date-and-time;
      config false;
      description
        "Last time when Keepalive packets were received from a peer.";
    }
    leaf negoHoldTime {
      type uint32 {
        range "0..65535";
      }
      config false;
      description
        "Hold time negotiated by BGP peers.";
    }
    leaf negoKeepAliveTime {
      type uint32 {
        range "0..21845";
      }
      config false;
      description
        "Keepalive time negotiated by BGP peers.";
    }
    leaf revUpdateCount {
      type uint32 {
        range "0..4294967295";
      }
      config false;
      description
        "Number of Update packets received from a peer.";
    }
    leaf revOpenCount {
      type uint32 {
        range "0..4294967295";
      }
      config false;
      description
        "Number of Open packets received from a peer.";
    }
    leaf revKeepAliveCount {
      type uint32 {
        range "0..4294967295";
      }
      config false;
      description
        "Number of Keepalive packets received from a peer.";
    }
    leaf revNotificationCount {
      type uint32 {
        range "0..4294967295";
      }
      config false;
      description
        "Number of Notification packets received from a peer.";
    }
    leaf revRouteRefreshCount {
      type uint32 {
        range "0..4294967295";
      }
      config false;
      description
        "Number of Route-Refresh packets received from a peer.";
    }
    leaf sentUpdateCount {
      type uint32 {
        range "0..4294967295";
      }
      config false;
      description
        "Number of Update packets sent to a peer.";
    }
    leaf sentOpenCount {
      type uint32 {
        range "0..4294967295";
      }
      config false;
      description
        "Number of Open packets sent to a peer.";
    }
    leaf sentKeepAliveCount {
      type uint32 {
        range "0..4294967295";
      }
      config false;
      description
        "Number of Keepalive packets sent to a peer.";
    }
    leaf sentNotificationCount {
      type uint32 {
        range "0..4294967295";
      }
      config false;
      description
        "Number of Notification packets sent to a peer.";
    }
    leaf sentRouteRefreshCount {
      type uint32 {
        range "0..4294967295";
      }
      config false;
      description
        "Number of Route-Refresh packets sent to a peer.";
    }
    leaf sendGRCapability {
      type boolean;
      config false;
      description
        "Whether the local end supports RR.";
    }
    leaf revRefreshCapability {
      type boolean;
      config false;
      description
        "Whether the peer supports RR.";
    }
    leaf revFourByteASCapability {
      type boolean;
      config false;
      description
        "Whether the peer supports 4-byte AS numbers.";
    }
    leaf revSupportMPCapability {
      type boolean;
      config false;
      description
        "Whether the peer supports MP.";
    }
    leaf revGRCapability {
      type boolean;
      config false;
      description
        "Whether the peer supports GR.";
    }
    leaf prefRecv {
      type uint32 {
        range "0..4294967295";
      }
      config false;
      description
        "Number of received route prefixes.";
    }
    leaf activePrefRecv {
      type uint32 {
        range "0..4294967295";
      }
      config false;
      description
        "Number of received prefixes of active routes.";
    }
    leaf prefAdvertised {
      type uint32 {
        range "0..4294967295";
      }
      config false;
      description
        "Number of advertised route prefixes.";
    }
  }
  grouping bgp_bgpcomm_peerLogInfos_type {
    description
      "";
    list peerLogInfo {
      key "logIndex";
      config false;
      description
        "Peer log information. After the log function is enabled on a peer, you can check the recorded log information about the peer.";
      leaf logIndex {
        type uint32;
        config false;
        description
          "Index of peer log information.";
      }
      leaf stateEvent {
        type string {
          length "0..20";
        }
        config false;
        description
          "Status of a peer when an event occurs.";
      }
      leaf errorCode {
        type uint8 {
          range "0..255";
        }
        config false;
        description
          "Error code that triggers an event.";
      }
      leaf errorSubCode {
        type uint8 {
          range "0..255";
        }
        config false;
        description
          "Error subcode that triggers an event.";
      }
      leaf notification {
        type string {
          length "0..40";
        }
        config false;
        description
          "Sent or received notification messages.";
      }
      leaf logDateTime {
        type yang:date-and-time;
        config false;
        description
          "Time when the log information was recorded.";
      }
    }
  }
  grouping bgp_bgpcomm_peerBfd_type {
    description
      "BGP Peer BFD configure class";
    leaf isBfdBlock {
      type boolean;
      default "false";
      description
        "Prevent  a BGP peer from inheriting the BFD configuration of the BGP peer group.";
    }
    leaf multiplier {
      type uint32 {
        range "3..50";
      }
      default "3";
      description
        "Specify the detection multiplier. The default value is 3.";
      ext:allowDelete "true";
    }
    leaf isBfdEnable {
      type boolean;
      default "false";
      description
        "Enable BFD.";
    }
    leaf rxInterval {
      type uint32 {
        range "3..1000";
      }
      description
        "Specify the minimum interval at which BFD packets are received. By default, the value is determined by the PAF file.";
      ext:allowDelete "true";
    }
    leaf txInterval {
      type uint32 {
        range "3..1000";
      }
      description
        "Specify the minimum interval at which BFD packets are sent. By default, the value is determined by the PAF file.";
      ext:allowDelete "true";
    }
    leaf isSingleHop {
      type boolean;
      must "not(../isBfdEnable='false') or (../isBfdEnable='false' and ../isSingleHop='false')";
      default "false";
      description
        "The single hop mode is preferred during the BFD session establishment between IBGP peers.";
    }
  }
  grouping bgp_bgpcomm_peerMembers_type {
    description
      "";
    list peerMember {
      key "peerSession";
      config false;
      description
        "Member in a peer group.";
      leaf peerSession {
        type string {
          length "1..512";
        }
        config false;
        description
          "Specify the address of the peer joining the peer group.";
      }
    }
  }
  grouping bgp_bgpcomm_peerAFMembers_type {
    description
      "";
    list peerAFMember {
      key "peer";
      config false;
      description
        "Peer in the peer address family.";
      leaf peer {
        type string {
          length "1..512";
        }
        config false;
        description
          "Peer address in the peer address family.";
      }
    }
  }
  grouping bgp_bgpcomm_peerGroupBfd_type {
    description
      "BGP Peer BFD Group configure class";
    leaf multiplier {
      type uint32 {
        range "3..50";
      }
      default "3";
      description
        "Specify the detection multiplier. The default value is 3.";
      ext:allowDelete "true";
    }
    leaf isBfdEnable {
      type boolean;
      default "false";
      description
        "Configure BFD.";
    }
    leaf rxInterval {
      type uint32 {
        range "3..1000";
      }
      description
        "Specify the minimum interval at which BFD packets are received. By default, the value is determined by the PAF file.";
      ext:allowDelete "true";
    }
    leaf txInterval {
      type uint32 {
        range "3..1000";
      }
      description
        "Specify the minimum interval at which BFD packets are sent. By default, the value is determined by the PAF file.";
      ext:allowDelete "true";
    }
    leaf isSingleHop {
      type boolean;
      must "not(../isBfdEnable='false') or (../isBfdEnable='false' and ../isSingleHop='false')";
      default "false";
      description
        "The single hop mode is preferred during the BFD session establishment between IBGP peers.";
    }
  }
  grouping bgp_bgpcomm_bgpVrfAFBriefInfoInfo_type {
    description
      "Display the brief information of the instance address family";
    leaf peerNum {
      type uint32;
      config false;
      description
        "Set the number of peers in a specified address family.";
    }
    leaf routeNum {
      type uint32;
      config false;
      description
        "Set the number of routes in a specified address family.";
    }
  }
}
