/*
Copyright (C) 2013-2017 Huawei Technologies Co., Ltd. All rights reserved.
*/
module huawei-ifm-deviations {
  namespace "http://www.huawei.com/netconf/vrp/huawei-ifm-deviations";
  prefix "huawei-ifm-deviations";

  import huawei-ifm {
    prefix "ifm";
  }

  organization
    "Huawei Technologies Co.,Ltd.";
  contact
    "Huawei Industrial Base Bantian, Longgang Shenzhen 518129                    
        People's Republic of China                    
        Website: http://www.huawei.com Email: support@huawei.com";
  description
    "Common interface management, which includes the public configuration of interfaces.";
  revision 2017-03-23 {
    description
      "Functions supported by the schema are added to the YANG file.";
    reference
      "Huawei private.";
  }
  revision 2013-01-01 {
    description
      "Init revision";
    reference
      "Huawei private.";
  }
  
  deviation /ifm:ifm/ifm:interfaces/ifm:interface/ifm:ifBandwidth {
    deviate not-supported;
  }
}
