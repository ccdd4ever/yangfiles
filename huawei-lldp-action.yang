/*
Copyright (C) 2013-2017 Huawei Technologies Co., Ltd. All rights reserved.
*/
submodule huawei-lldp-action {
  belongs-to huawei-lldp {
    prefix lldp;
  }
  import huawei-pub-type {
    prefix pub-type;
  }
  include huawei-lldp-type;
  
  organization
    "Huawei Technologies Co.,Ltd.";
  contact
    "Huawei Industrial Base Bantian, Longgang Shenzhen 518129                    
        People's Republic of China                    
        Website: http://www.huawei.com Email: support@huawei.com";
  description
    "lldp_action";
  revision 2017-03-23 {
    description
      "Functions supported by the schema are added to the YANG file.";
    reference
      "Huawei private.";
  }
  revision 2013-01-01 {
    description
      "Init revision";
    reference
      "Huawei private.";
  }
  rpc resetMdnStatistics {
    description
      "Reset interface MDN statistics.";
    input {
      leaf ifName {
        type pub-type:ifName;
        description
          "Port name.";
      }
    }
  }
  rpc resetlldpStatistics {
    description
      "Reset interface LLDP statistics.";
    input {
      leaf ifName {
        type pub-type:ifName;
        description
          "Port name.";
      }
    }
  }
  rpc clearLldpNeighbor {
    description
      "Clear interface LLDP neighbors.";
    input {
      leaf ifName {
        type pub-type:ifName;
        description
          "Port name.";
      }
    }
  }
  rpc resetAllLldpStatistics {
    description
      "Reset all interface LLDP statistics.";
  }
  rpc resetAllMdnStatistics {
    description
      "Reset all interface MDN statistics.";
  }
  rpc clearAllLldpNeighbor {
    description
      "Clear all interface LLDP neighbors.";
  }
}
