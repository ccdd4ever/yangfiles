/*
Copyright (C) 2013-2017 Huawei Technologies Co., Ltd. All rights reserved.
*/
submodule huawei-telnets-type {
  belongs-to huawei-telnets {
    prefix telnets;
  }
  
  organization
    "Huawei Technologies Co.,Ltd.";
  contact
    "Huawei Industrial Base Bantian, Longgang Shenzhen 518129                    
        People's Republic of China                    
        Website: http://www.huawei.com Email: support@huawei.com";
  description
    "Description of telnet server type submodule";
  revision 2017-03-23 {
    description
      "Functions supported by the schema are added to the YANG file.";
    reference
      "Huawei private.";
  }
  revision 2013-01-01 {
    description
      "Init revision";
    reference
      "Huawei private.";
  }
  typedef telnetsTlntSvrDbgType {
    type string;
    description
      "TELNET server service debug type list";
  }
  typedef telnetsTlntAuthMode {
    type enumeration {
      enum "None" {
        description
          "None:";
      }
      enum "AAA" {
        description
          "AAA:";
      }
      enum "Password" {
        description
          "Password:";
      }
    }
    description
      "TELNET server authentication mode list";
  }
}
