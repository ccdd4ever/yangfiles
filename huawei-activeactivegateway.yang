/*
Copyright (C) 2013-2017 Huawei Technologies Co., Ltd. All rights reserved.
*/
module huawei-activeactivegateway {
  namespace "http://www.huawei.com/netconf/vrp/huawei-activeactivegateway";
  prefix activeactivegateway;
  import huawei-pub-type {
    prefix pub-type;
  }
  import ietf-inet-types {
    prefix inet;
  }
  include huawei-activeactivegateway-type;
  
  organization
    "Huawei Technologies Co.,Ltd.";
  contact
    "Huawei Industrial Base Bantian, Longgang Shenzhen 518129                    
        People's Republic of China                    
        Website: http://www.huawei.com Email: support@huawei.com";
  description
    "active-active-gateway.";
  revision 2017-03-23 {
    description
      "Functions supported by the schema are added to the YANG file.";
    reference
      "Huawei private.";
  }
  revision 2013-01-01 {
    description
      "Init revision";
    reference
      "Huawei private.";
  }
  container activeactivegateway {
    description
      "active-active-gateway.";
    container gatewayInstances {
      description
        "active-active-gateway.";
      list gatewayInstance {
        key "dfsgroupId peerAddr";
        max-elements  "3";
        description
          "active-active-gateway.";
        leaf dfsgroupId {
          type uint32 {
            range "1..2";
          }
          description
            "Dynamic Fabric Service Group ID.";
        }
        leaf peerAddr {
          type inet:ipv4-address-no-zone;
          description
            "Address.";
        }
        leaf peervpnName {
          type string {
            length "0..32";
          }
          description
            "Vpn-instance.";
        }
        leaf systemName {
          type string {
            length "0..50";
          }
          config false;
          description
            "System Name.";
        }
        leaf state {
          type state;
          config false;
          description
            "State.";
        }
        leaf duration {
          type pub-type:timeTick;
          config false;
          description
            "Duration.";
        }
      }
    }
  }
}
