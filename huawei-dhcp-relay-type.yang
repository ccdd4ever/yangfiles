/*
Copyright (C) 2013-2017 Huawei Technologies Co., Ltd. All rights reserved.
*/
submodule huawei-dhcp-relay-type {
  belongs-to huawei-dhcp {
    prefix dhcp;
  }
  
  organization
    "Huawei Technologies Co.,Ltd.";
  contact
    "Huawei Industrial Base Bantian, Longgang Shenzhen 518129                    
        People's Republic of China                    
        Website: http://www.huawei.com Email: support@huawei.com";
  description
    "test.Description FOR submodule";
  revision 2017-03-23 {
    description
      "Functions supported by the schema are added to the YANG file.";
    reference
      "Huawei private.";
  }
  revision 2013-01-01 {
    description
      "Init revision";
    reference
      "Huawei private.";
  }
  typedef dhcpRelayServerPolicy {
    type enumeration {
      enum "load balance" {
        description
          "Load balancing.";
      }
      enum "broadcast" {
        description
          "Broadcast.";
      }
    }
    description
      "description of dhcp_dhcpRelayServerPolicy_type";
  }
  typedef dhcpRelayReplyType {
    type enumeration {
      enum "Invalid" {
        description
          "-";
      }
      enum "broadcast-always" {
        description
          "Always broadcast the reply";
      }
    }
    description
      "description of dhcp_dhcpRelayReplyType_type";
  }
  typedef dhcpOpt82VendorSubOptFmt {
    type string;
    description
      "description of dhcp_dhcpOpt82VendorSubOptFmt_type";
  }
  typedef dhcpOpt82Sub6Fmt {
    type enumeration {
      enum "invalid" {
        description
          "-";
      }
      enum "self-define" {
        description
          "self-define";
      }
    }
    description
      "description of dhcp_dhcpOpt82Sub6Fmt_type";
  }
}
