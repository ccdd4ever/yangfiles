/*
Copyright (C) 2013-2017 Huawei Technologies Co., Ltd. All rights reserved.
*/
module huawei-dsa {
  namespace "http://www.huawei.com/netconf/vrp/huawei-dsa";
  prefix dsa;
  import huawei-extension {
    prefix ext;
  }
  include huawei-dsa-type;
  
  organization
    "Huawei Technologies Co.,Ltd.";
  contact
    "Huawei Industrial Base Bantian, Longgang Shenzhen 518129                    
        People's Republic of China                    
        Website: http://www.huawei.com Email: support@huawei.com";
  description
    "DSA";
  revision 2017-03-23 {
    description
      "Functions supported by the schema are added to the YANG file.";
    reference
      "Huawei private.";
  }
  revision 2013-01-01 {
    description
      "Init revision";
    reference
      "Huawei private.";
  }
  container dsa {
    description
      "DSA";
    container dsaLocalKeys {
      description
        "Local key table";
      container dsaLocalKey {
        description
          "Local key code.";
        leaf keySize {
          type dsaDSAKeyType;
          default "2048";
          description
            "key size";
        }
        leaf hostKeyName {
          type string {
            length "0..264";
          }
          config false;
          description
            "Hostkey name";
        }
        leaf hostKeyCode {
          type string {
            length "0..2048";
          }
          config false;
          description
            "Hostkey code";
        }
        leaf hostKeyPEM {
          type string {
            length "0..2048";
          }
          config false;
          description
            "Hostkey code in PEM format";
        }
        leaf hostKeyOpenSSH {
          type string {
            length "0..2048";
          }
          config false;
          description
            "Hostkey code in OpenSSH format";
        }
      }
    }
    container dsaPeerKeys {
      description
        "Peer key table";
      list dsaPeerKey {
        key "keyName";
        description
          "Peer key code.";
        leaf keyName {
          type string {
            length "1..30";
          }
          description
            "Key name";
        }
        leaf keyCode {
          type string {
            length "1..2047";
          }
          mandatory true;
          description
            "Key code";
        }
        leaf encodeInType {
          type dsaEncodeInType;
          mandatory true;
          description
            "Encode type";
        }
      }
    }
    container dsaKeyPairCfgs {
      description
        "DSA keypair labels";
      list dsaKeyPairCfg {
        key "keyPairLabel";
        max-elements  "20";
        description
          "DSA keypair label";
        leaf keyPairLabel {
          type string {
            length "0..35";
            pattern '[a-zA-Z0-9_]*';
          }
          description
            "Keypair Label Name : It only contains underscores (_), case-insensitive letters and digits";
        }
        leaf keySize {
          type dsaDSAKeyType;
          mandatory true;
          description
            "Size of Keypair";
        }
        leaf hostKeyCode {
          type string {
            length "0..2048";
          }
          config false;
          description
            "DSA hostkey code";
        }
      }
    }
    container dsaGlobalCfg {
      description
        "Global Configuration ";
      leaf maxKeyPair {
        type int32 {
          range "1..20";
        }
        default "20";
        description
          "Maximum keypair value";
        ext:allowDelete "true";
      }
    }
  }
}
