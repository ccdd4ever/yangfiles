/*
Copyright (C) 2013-2017 Huawei Technologies Co., Ltd. All rights reserved.
*/
submodule huawei-mac-action {
  belongs-to huawei-mac {
    prefix mac;
  }
  include huawei-mac-type;
  
  organization
    "Huawei Technologies Co.,Ltd.";
  contact
    "Huawei Industrial Base Bantian, Longgang Shenzhen 518129                    
        People's Republic of China                    
        Website: http://www.huawei.com Email: support@huawei.com";
  description
    "Description FOR submodule";
  revision 2017-03-23 {
    description
      "Functions supported by the schema are added to the YANG file.";
    reference
      "Huawei private.";
  }
  revision 2013-01-01 {
    description
      "Init revision";
    reference
      "Huawei private.";
  }
  rpc delVlanMac {
    description
      "Delete Dynamic MAC address entries based on a VLAN ID.";
    input {
      leaf vlanId {
        type macVlanId;
        description
          "VLAN ID.";
      }
    }
  }
  rpc resetMflpRec {
    description
      "Reset MAC Flapping Records.";
    input {
      leaf isDelAll {
        type boolean;
        description
          "Reset All of The MAC Flapping Records.";
      }
    }
  }
}
