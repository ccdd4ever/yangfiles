/*
Copyright (C) 2013-2017 Huawei Technologies Co., Ltd. All rights reserved.
*/
submodule huawei-dhcp-server-action {
  belongs-to huawei-dhcp {
    prefix dhcp;
  }
  import ietf-inet-types {
    prefix inet;
  }
  import huawei-extension {
    prefix ext;
  }
  include huawei-dhcp-server-type;
  
  organization
    "Huawei Technologies Co.,Ltd.";
  contact
    "Huawei Industrial Base Bantian, Longgang Shenzhen 518129                    
        People's Republic of China                    
        Website: http://www.huawei.com Email: support@huawei.com";
  description
    "test.Description FOR submodule";
  revision 2017-03-23 {
    description
      "Functions supported by the schema are added to the YANG file.";
    reference
      "Huawei private.";
  }
  revision 2013-01-01 {
    description
      "Init revision";
    reference
      "Huawei private.";
  }
  rpc server-resetServerStatistics {
    description
      "Reset server statistics.";
  }
  rpc server-resetGlobalIpPool {
    description
      "Reset the global IP pool.";
    input {
      leaf poolName {
        type string {
          length "1..64";
        }
        description
          "Pool name.";
      }
      leaf startIp {
        type inet:ipv4-address-no-zone;
        mandatory true;
        description
          "Start IP address.";
        ext:allowDelete "true";
      }
      leaf endIp {
        type inet:ipv4-address-no-zone;
        description
          "End IP address.";
      }
      leaf addressType {
        type ipPoolAddressResetType;
        description
          "Address type.";
        ext:allowDelete "true";
      }
    }
  }
}
