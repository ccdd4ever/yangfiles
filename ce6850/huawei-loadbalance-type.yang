submodule huawei-loadbalance-type {
    belongs-to "huawei-loadbalance" {
        prefix "loadbalance";
    }
    
    organization "Huawei Technologies Co.,Ltd.";
    contact "Huawei Industrial Base Bantian, Longgang Shenzhen 518129                    
              People's Republic of China                    
              Website: http://www.huawei.com Email: support@huawei.com";
  revision 2017-03-23 {
    description
      "Functions supported by the schema are added to the YANG file.";
    reference
      "Huawei private.";
  }
  revision 2013-01-01 {
    description
      "Init revision";
    reference
      "Huawei private.";
  }
    typedef hashtype {
        description "";
        type enumeration {
            enum "dst-ip" {
                value 0;
                description "destination IP hash arithmetic ";
            }
            enum "dst-mac" {
                value 1;
                description "destination MAC hash arithmetic ";
            }
            enum "enhanced" {
                value 2;
                description "enhanced hash arithmetic";
            }
            enum "src-dst-ip" {
                value 3;
                description "source and destination IP hash arithmetic ";
            }
            enum "src-dst-mac" {
                value 4;
                description "source and destination MAC hash arithmetic ";
            }
            enum "src-ip" {
                value 5;
                description "source IP hash arithmetic";
            }
            enum "src-mac" {
                value 6;
                description "source MAC hash arithmetic ";
            }
            enum "resilient" {
                value 7;
                description "resilient profile name";
            }
        }
    }
    typedef trillegress {
        description "";
        type enumeration {
            enum "l2trillegress" {
                value 0;
                description "l2 trill egress hash type";
            }
            enum "ipv4trillegress" {
                value 1;
                description "ipv4 trill egress hash type";
            }
            enum "ipv6trillegress" {
                value 2;
                description "ipv6 trill egress hash type";
            }
        }
    }
    typedef LagSlotPath {
        description "slotPath is like 3, 1/3";
        type string {
            length "1..127";
            pattern '^(\d+/)?\d+$';
        }
    }
}
