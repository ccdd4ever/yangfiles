/*
Copyright (C) 2013-2017 Huawei Technologies Co., Ltd. All rights reserved.
*/
module huawei-feil3bd {
  namespace "http://www.huawei.com/netconf/vrp/huawei-feil3bd";
  prefix feil3bd;
  organization
    "Huawei Technologies Co.,Ltd.";
  contact
    "Huawei Industrial Base Bantian, Longgang Shenzhen 518129                    
        People's Republic of China                    
        Website: http://www.huawei.com Email: support@huawei.com";
  description
    "feil3bd";
  revision 2017-03-23 {
    description
      "Functions supported by the schema are added to the YANG file.";
    reference
      "Huawei private.";
  }
  revision 2013-01-01 {
    description
      "Init revision";
    reference
      "Huawei private.";
  }
  container feil3bd {
    description
      "feil3bd";
    container feil3arprederectcons {
      description
        "feil3arprederectcons";
      list feil3arprederectcon {
        key "bdId";
        description
          "feil3arprederectcon";
        leaf bdId {
          type uint32 {
            range "1..16777215";
          }
          description
            "bdId";
        }
        leaf arpControllerRedirectEnable {
          type boolean;
          default "false";
          description
            "arpControllerRedirectEnable";
        }
      }
    }
  }
}
