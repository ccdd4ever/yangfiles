/*
Copyright (C) 2013-2017 Huawei Technologies Co., Ltd. All rights reserved.
*/
submodule huawei-ecc-type {
  belongs-to huawei-ecc {
    prefix ecc;
  }
  
  organization
    "Huawei Technologies Co.,Ltd.";
  contact
    "Huawei Industrial Base Bantian, Longgang Shenzhen 518129                    
        People's Republic of China                    
        Website: http://www.huawei.com Email: support@huawei.com";
  description
    "Description of ecc type submodule";
  revision 2017-03-23 {
    description
      "Functions supported by the schema are added to the YANG file.";
    reference
      "Huawei private.";
  }
  revision 2013-01-01 {
    description
      "Init revision";
    reference
      "Huawei private.";
  }
  typedef eccECCKeyType {
    type enumeration {
      enum "256" {
        description
          "Modulus 256";
      }
      enum "384" {
        description
          "Modulus 384";
      }
      enum "521" {
        description
          "Modulus 521";
      }
    }
    description
      "Ecc key length";
  }
}
