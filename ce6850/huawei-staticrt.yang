/*
Copyright (C) 2013-2017 Huawei Technologies Co., Ltd. All rights reserved.
*/
module huawei-staticrt {
  namespace "http://www.huawei.com/netconf/vrp/huawei-staticrt";
  prefix staticrt;
  include huawei-staticrt-staticmrt-type;
  include huawei-staticrt-staticmrt;
  include huawei-staticrt-staticrtbase-type;
  include huawei-staticrt-staticrtbase;
  
  organization
    "Huawei Technologies Co.,Ltd.";
  contact
    "Huawei Industrial Base Bantian, Longgang Shenzhen 518129                    
        People's Republic of China                    
        Website: http://www.huawei.com Email: support@huawei.com";
  description
    "Add static routes to the RM routing table.";
  revision 2017-03-23 {
    description
      "Functions supported by the schema are added to the YANG file.";
    reference
      "Huawei private.";
  }
  revision 2013-01-01 {
    description
      "Init revision";
    reference
      "Huawei private.";
  }
  container staticrt {
    description
      "Add static routes to the RM routing table.";
    container staticrtbase {
      description
        "Basic service package for static routes.";
      uses staticrt:staticrt_staticrtbase_type;
    }
    container staticmrt {
      description
        "Basic Service Package of Static Multicast Routes.";
      uses staticrt:staticrt_staticmrt_type;
    }
  }
}
