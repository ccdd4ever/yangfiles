/*
Copyright (C) 2013-2017 Huawei Technologies Co., Ltd. All rights reserved.
*/
module huawei-pp4-deviations-cx {
  namespace "http://www.huawei.com/netconf/vrp/huawei-pp4-deviations-cx";
  prefix "pp4-devs-cx";

  import huawei-pp4 {
    prefix "pp4";
  }

  organization
    "Huawei Technologies Co.,Ltd.";
  contact
    "Huawei Industrial Base Bantian, Longgang Shenzhen 518129                    
        People's Republic of China                    
        Website: http://www.huawei.com Email: support@huawei.com";
  description
    "IPv4.";
  revision 2013-01-01 {
    description
      "Init revision";
    reference
      "Huawei private.";
  }

  deviation /pp4:pp4/pp4:icmpRedirectInterfaces/pp4:icmpRedirectInterface/pp4:ifRdrctSndEn {
    deviate not-supported;
  }

}
