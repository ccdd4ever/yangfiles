/*
Copyright (C) 2013-2017 Huawei Technologies Co., Ltd. All rights reserved.
*/
submodule huawei-qos-wred-type {
  belongs-to "huawei-qos" {
    prefix "qos";
  }
  
  organization "Huawei Technologies Co.,Ltd.";
  contact "Huawei Industrial Base Bantian, Longgang Shenzhen 518129                    
              People's Republic of China                    
              Website: http://www.huawei.com Email: support@huawei.com";
  revision 2017-03-23 {
    description
      "Functions supported by the schema are added to the YANG file.";
    reference
      "Huawei private.";
  }
  revision 2013-01-01 {
    description
      "Init revision";
    reference
      "Huawei private.";
  }
  typedef qosMacType {
    type enumeration {
      enum "source" {
        description
          "source:";
      }
      enum "destination" {
        description
          "destination:";
      }
    }
  }
}
