submodule huawei-dad-type {
    belongs-to "huawei-dad" {
        prefix "dad";
    }
    
    organization "Huawei Technologies Co.,Ltd.";
    contact "Huawei Industrial Base Bantian, Longgang Shenzhen 518129                    
              People's Republic of China                    
              Website: http://www.huawei.com Email: support@huawei.com";
  revision 2017-03-23 {
    description
      "Functions supported by the schema are added to the YANG file.";
    reference
      "Huawei private.";
  }
  revision 2013-01-01 {
    description
      "Init revision";
    reference
      "Huawei private.";
  }
    typedef dadStatusType {
        type enumeration {
            enum "Normal" {
                value 0;
                description "Normal.";
            }
            enum "Conflict" {
                value 1;
                description "Conflict.";
            }
            enum "Initial" {
                value 2;
                description "Initial.";
            }
        }
    }
    typedef dadModeType {
        type enumeration {
            enum "Direct" {
                value 0;
                description "Direct.";
            }
            enum "Relay" {
                value 1;
                description "Relay.";
            }
        }
    }
    typedef dadMethStatusType {
        type enumeration {
            enum "Disable" {
                value 0;
                description "Disable.";
            }
            enum "Enable" {
                value 1;
                description "Enable.";
            }
        }
    }
}
