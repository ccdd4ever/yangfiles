/*
Copyright (C) 2013-2017 Huawei Technologies Co., Ltd. All rights reserved.
*/
submodule huawei-ifm-type {
  belongs-to huawei-ifm {
    prefix ifm;
  }
  
  organization
    "Huawei Technologies Co.,Ltd.";
  contact
    "Huawei Industrial Base Bantian, Longgang Shenzhen 518129                    
        People's Republic of China                    
        Website: http://www.huawei.com Email: support@huawei.com";
  description
    "the ifm type submodule";
  revision 2017-03-23 {
    description
      "Functions supported by the schema are added to the YANG file.";
    reference
      "Huawei private.";
  }
  revision 2013-01-01 {
    description
      "Init revision";
    reference
      "Huawei private.";
  }
  typedef ifmcommPhyType {
    type enumeration {
      enum "Ethernet" {
        description
          "Ethernet interface.";
      }
      enum "Eth-Trunk" {
        description
          "Eth-Trunk interface.";
      }
      enum "Tunnel" {
        description
          "Tunnel interface.";
      }
      enum "NULL" {
        description
          "Null interface.";
      }
      enum "LoopBack" {
        description
          "Loopback interface.";
      }
      enum "Vlanif" {
        description
          "VLANIF interface.";
      }
      enum "100GE" {
        description
          "100 GigabitEthernet interface.";
      }
      enum "40GE" {
        description
          "40 GigabitEthernet interface.";
      }
      enum "10GE" {
        description
          "10 GigabitEthernet interface.";
      }
      enum "GEBrief" {
        description
          "GigabitEthernet interface.";
      }
      enum "MEth" {
        description
          "Management Ethernet interface.";
      }
      enum "Stack-Port" {
        description
          "Stack-port interface.";
      }
      enum "Sip" {
        description
          "System interconnect port.";
      }
      enum "Fabric-Port" {
        description
          "Fabric-Port interface.";
      }
      enum "FCoE-Port" {
        description
          "FCoE-Port Interface.";
      }
      enum "4x10GE" {
        description
          "4x10 GigabitEthernet interface.";
      }
    }
    description
      "ifmcommRouterType is like Ethernet/Eth-Trunk/...";
  }
  typedef ifmcommRouterType {
    type enumeration {
      enum "PtoP" {
        description
          "Point to point.";
      }
      enum "Broadcast" {
        description
          "Broadcast.";
      }
    }
    description
      "ifmcommRouterType is like NBMA/Broadcast/...";
  }
  typedef ifmcommAdminStaType {
    type enumeration {
      enum "up" {
        description
          "Administratively Up.";
      }
      enum "down" {
        description
          "Administratively Down.";
      }
    }
    description
      "ifmcommAdminStaType is like up/down";
  }
  typedef ifmcommNetWorkLayerState {
    type enumeration {
      enum "ipv4andipv6up" {
        description
          "Administratively Up of  ipv4 and ipv6 state.";
      }
      enum "ipv4andipv6down" {
        description
          "Administratively Down of ipv4 and ipv6 state.";
      }
    }
    description
      "ifmcommAdminStaType is like up/down";
  }
  typedef ifmcommLinkProtocol {
    type enumeration {
      enum "ethernet" {
        description
          "The link protocol of the interface is Ethernet.";
      }
      enum "invalid" {
        description
          "None.";
      }
    }
    description
      "ifmcommLinkProtocol is like ppp/hdlc/fr";
  }
  typedef ifmcommIfStatus {
    type enumeration {
      enum "up" {
        description
          "The interface is in Up state.";
      }
      enum "down" {
        description
          "The interface is in Down state.";
      }
    }
    description
      "ifmcommIfStatus is like up/down";
  }
  typedef ifmam4IpAddrType {
    type enumeration {
      enum "main" {
        description
          "Primary address of an interface.";
      }
      enum "sub" {
        description
          "Secondary address of an interface.";
      }
      enum "unnumber" {
        description
          "Unnumbered address of an interface.";
      }
    }
    description
      "ifmam4IpAddrType is like main/sub";
  }
  typedef ifmam4CfgType {
    type enumeration {
      enum "config" {
        description
          "Configured address.";
      }
      enum "unnumbered" {
        description
          "Unnumbered address.";
      }
    }
    description
      "ifmam4CfgType is like config/unnumbered/negotiation";
  }
  typedef ifmam4IpAddrCreateOrDelete {
    type enumeration {
      enum "Config" {
        description
          "The IP address is manually configured.";
      }
      enum "Delete" {
        description
          "No IP address is allocated.";
      }
    }
    description
      "ifmam4IpAddrCreateOrDelete is like Config/Delete";
  }
  typedef ifmam6IpAddr6Type {
    type enumeration {
      enum "global" {
        description
          "Global unicast address.";
      }
      enum "linkLocal" {
        description
          "Link local address.";
      }
      enum "anycast" {
        description
          "Anycast address.";
      }
    }
    description
      "ifmam6IpAddr6Type is like linklocal/global/ndPrefix";
  }
  typedef ifmam6IDGenType {
    type enumeration {
      enum "none" {
        description
          "none.";
      }
      enum "cga" {
        description
          "CGA.";
      }
      enum "eui64" {
        description
          "EUI 64.";
      }
    }
    description
      "ifmam6IDGenType is like none/cga/eui64";
  }
  typedef ifmcommServiceType {
    type enumeration {
      enum "None" {
        description
          "None.";
      }
      enum "TrunkMember" {
        description
          "Trunk member.";
      }
      enum "StackMember" {
        description
          "Stack member.";
      }
      enum "FabricMember" {
        description
          "Fabric member";
      }
    }
    description
      "ifmcommServiceType is like manageport/trunkmember/l2ser/l3ser/l2switch";
  }
  typedef ifmcommErrorDownType {
    type enumeration {
      enum "bpdu-protection" {
        description
          "BPDU protection.";
      }
      enum "auto-defend" {
        description
          "Attack source tracing.";
      }
      enum "monitor-link" {
        description
          "The uplink of monitor-link group is down.";
      }
      enum "loopback-detect" {
        description
          "Loopback detect.";
      }
      enum "portsec-reachedlimit" {
        description
          "Secure MAC addresses have reached the upper limit.";
      }
      enum "mac-address-flapping" {
        description
          "MAC address flapping.";
      }
      enum "storm-control" {
        description
          "Storm-control.";
      }
      enum "dual-active" {
        description
          "Dual-active.";
      }
      enum "crc-statistics" {
        description
          "CRC statistics.";
      }
      enum "transceiver-power-low" {
        description
          "The transceiver power is low.";
      }
      enum "link-flap" {
        description
          "Link flapping.";
      }
      enum "stack-member-exceed-limit" {
        description
          "The number of stack members exceeds the limit.";
      }
      enum "spine-member-exceed-limit" {
        description
          "The number of spine members exceeds the limit.";
      }
      enum "resource-mismatch" {
        description
          "Resource mismatch.";
      }
      enum "m-lag" {
        description
          "M-LAG peer detect error.";
      }
      enum "stack-config-conflict" {
        description
          "Stack config conflict.";
      }
      enum "spine-type-unsupported" {
        description
          "Spine type unsupported.";
      }
      enum "stack-packet-defensive" {
        description
          "Stack packet defensive.";
      }
      enum "forward-engine-buffer-failed" {
        description
          "Forward engine buffer failed.";
      }
      enum "forward-engine-interface-failed" {
        description
          "Forward engine interface failed.";
      }
      enum "m-lag-consistency-check" {
        description
          "M-Lag consistency check failed.";
      }
      enum "invalid" {
        description
          "None.";
      }
    }
    description
      "ifmcommErrorDownType is like bpdu-protection";
  }
  typedef veInterfaceType {
    type enumeration {
      enum "L2VE" {
        description
          "Layer 2 Virtual-Ethernet interface.";
      }
      enum "L3VE" {
        description
          "Layer 3 Virtual-Ethernet interface.
";
      }
      enum "invalid" {
        description
          "None.
";
      }
    }
    description
      "veIfType is like L2VE/L3VE";
  }
  typedef veForwarModeType {
    type enumeration {
      enum "through" {
        description
          "Software loopback.";
      }
      enum "loopback" {
        description
          "Hardware loopback.";
      }
      enum "invalid" {
        description
          "None.";
      }
    }
    description
      "veForwarMode is like through/loopback";
  }
  typedef ifIpStatiModeType {
    type enumeration {
      enum "forward" {
        description
          "Forward mode statistics.";
      }
      enum "mac" {
        description
          "MAC mode statistics.";
      }
      enum "invalid" {
        description
          "None.";
      }
    }
    description
      "fei statistic mode type";
  }
  typedef ifmcommIfClassType {
    type enumeration {
      enum "mainInterface" {
        description
          "Main Interface.";
      }
      enum "subInterface" {
        description
          "Sub-interface.";
      }
    }
    description
      "ifmcommIfClassType is like mainInterface/...";
  }
  typedef ifmcommControlMtu {
    type enumeration {
      enum "1450" {
        description
          "1450.0";
      }
      enum "1500" {
        description
          "1500.0";
      }
    }
    description
      "device Control Mtu/...";
  }
  typedef ifmcommEncapType {
    type enumeration {
      enum "vlanType" {
        description
          "VLAN type.";
      }
      enum "dot1q" {
        description
          "Dot1q.";
      }
      enum "qinq" {
        description
          "QinQ.";
      }
      enum "p2p" {
        description
          "P2P.";
      }
      enum "p2mp" {
        description
          "P2MP.";
      }
      enum "l2ve" {
        description
          "L2VE.";
      }
      enum "l3ve" {
        description
          "L3VE.";
      }
      enum "vlanTypePolicy" {
        description
          "VLAN type policy.";
      }
      enum "dot1qPolicy" {
        description
          "Dot1q policy.";
      }
      enum "stackingPolicy" {
        description
          "Stacking policy.";
      }
      enum "untagPolicy" {
        description
          "Untag policy.";
      }
      enum "qinqMapping" {
        description
          "QinQ mapping.";
      }
      enum "l2vc" {
        description
          "L2VC.";
      }
      enum "l3vc" {
        description
          "L3VC.";
      }
      enum "evcUntag" {
        description
          "EvcUntag.";
      }
      enum "evcDot1q" {
        description
          "EvcDot1q.";
      }
      enum "evcQinq" {
        description
          "EvcQinq.";
      }
      enum "evcDefault" {
        description
          "EvcDefault.";
      }
      enum "evcDot1qPolicy" {
        description
          "EvcDot1qPolicy.";
      }
      enum "ietf" {
        description
          "IETF.";
      }
      enum "nonstandard" {
        description
          "Nonstandard.";
      }
      enum "invalid" {
        description
          "Invalid.";
      }
    }
    description
      "fr encap type";
  }
  typedef ifmcommStatMode {
    type string;
    description
      "ifmcommStatMode is like baseInterface/baseVlanGroup";
  }
  typedef ifmcommPortMode {
    type enumeration {
      enum "Mix" {
        description
          "Mix Port Mode";
      }
      enum "L2" {
        description
          "L2 Port Mode";
      }
      enum "L3" {
        description
          "L3 Port Mode";
      }
    }
    description
      "ifmcommPortMode is like L2/L3/MIX";
  }
  typedef transAlarmDownType {
    type enumeration {
      enum "enable" {
        description
          "Enable Transmission-Alarm Down";
      }
      enum "disable" {
        description
          "Disable Transmission-Alarm Down";
      }
    }
    description
      "transAlarmDownType is like enable/disable";
  }
  typedef ifmcommDampLevelType {
    type enumeration {
      enum "light" {
        description
          "Light weight";
      }
      enum "middle" {
        description
          "Middle weight";
      }
      enum "heavy" {
        description
          "Heavy weight";
      }
      enum "manual" {
        description
          "Manually configure the parameters";
      }
    }
    description
      "ifmcommDampLevelType is light/middle/heavy/manual";
  }
  typedef ifmMacAddress {
    type string {
      length "0..14";
      pattern '[0-9a-fA-F]{4}(-[0-9a-fA-F]{4}){2}';
    }
    description
      "A MAC address in standard notation";
  }
  typedef ifmIpv4Mask {
    type string {
      length "1..15";
      pattern '((([1-9]?[0-9]|1[0-9][0-9]|2[0-4][0-9]|25[0-5])\.){3}([1-9]?[0-9]|1[0-9][0-9]|2[0-4][0-9]|25[0-5]))';
    }
    description
      "ipv4Mask support mask format";
  }
}
