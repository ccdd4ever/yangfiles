/*
Copyright (C) 2013-2017 Huawei Technologies Co., Ltd. All rights reserved.
*/
submodule huawei-dhcp-relay-action {
  belongs-to huawei-dhcp {
    prefix dhcp;
  }
  import huawei-pub-type {
    prefix pub-type;
  }
  import ietf-inet-types {
    prefix inet;
  }
  import huawei-extension {
    prefix ext;
  }
  organization
    "Huawei Technologies Co.,Ltd.";
  contact
    "Huawei Industrial Base Bantian, Longgang Shenzhen 518129                    
        People's Republic of China                    
        Website: http://www.huawei.com Email: support@huawei.com";
  description
    "test.Description FOR submodule";
  revision 2017-03-23 {
    description
      "Functions supported by the schema are added to the YANG file.";
    reference
      "Huawei private.";
  }
  revision 2013-01-01 {
    description
      "Init revision";
    reference
      "Huawei private.";
  }
  rpc relay-resetDhcpRelayStatistics {
    description
      "Reset DHCP relay statistics.";
  }
  rpc relay-resetDhcpRelaySerGrpstat {
    description
      "Clear DHCP relay statistics of server groups.";
    input {
      leaf serverGroupName {
        type string {
          length "1..32";
        }
        description
          "DHCP server group name.";
      }
    }
  }
  rpc relay-releaseClient {
    description
      "DHCP relay release.";
    input {
      leaf clientIpAddr {
        type inet:ipv4-address-no-zone;
        description
          "Client IP address to be released.";
        ext:allowDelete "false";
      }
      leaf clientMAC {
        type pub-type:macAddress;
        mandatory true;
        description
          "Client MAC address to be released.";
      }
      leaf serverIpAddr {
        type inet:ipv4-address-no-zone;
        mandatory true;
        description
          "Server address.";
      }
      leaf interfaceName {
        type pub-type:ifName;
        description
          "Interface name.";
        ext:allowDelete "true";
      }
      leaf vrfName {
        type pub-type:vrfName;
        description
          "VPN name.";
        ext:allowDelete "true";
      }
    }
  }
}
