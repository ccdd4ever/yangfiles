/*
Copyright (C) 2013-2017 Huawei Technologies Co., Ltd. All rights reserved.
*/
module huawei-vlan {
  namespace "http://www.huawei.com/netconf/vrp/huawei-vlan";
  prefix vlan;
  import huawei-pub-type {
    prefix pub-type;
  }
  import huawei-extension {
    prefix ext;
  }
  include huawei-vlan-action;
  include huawei-vlan-type;
  
  organization
    "Huawei Technologies Co.,Ltd.";
  contact
    "Huawei Industrial Base Bantian, Longgang Shenzhen 518129                    
        People's Republic of China                    
        Website: http://www.huawei.com Email: support@huawei.com";
  description
    "VLAN management.";
  revision 2017-03-23 {
    description
      "Functions supported by the schema are added to the YANG file.";
    reference
      "Huawei private.";
  }
  revision 2013-01-01 {
    description
      "Init revision";
    reference
      "Huawei private.";
  }
  container vlan {
    description
      "VLAN management.";
    container vlans {
      description
        "VLAN list.";
      list vlan {
        key "vlanId";
        max-elements  "4094";
        description
          "VLAN information.";
        leaf vlanId {
          type vlanId {
            range "1..4094";
          }
          description
            "VLAN ID.";
        }
        leaf vlanName {
          type string {
            length "1..31";
          }
          must "not(../vlanType='carrier' or ../vlanType='fcoe')";
          description
            "VLAN name.";
          ext:allowDelete "true";
        }
        leaf vlanDesc {
          type string {
            length "1..80";
          }
          must "not(../vlanType='carrier' or ../vlanType='fcoe')";
          description
            "VLAN description.";
          ext:allowDelete "true";
        }
        leaf vlanType {
          type vlanType;
          must "((../vlanType='common' or ../vlanType='super' or ../vlanType='principal') ) or (../vlanType='common' and (../vlanType='common' or ../vlanType='super' or ../vlanType='principal') ) or (../vlanType='group' and (../vlanType='common' or ../vlanType='group') ) or (../vlanType='principal' and (../vlanType='common' or ../vlanType='principal') ) or (../vlanType='seperate' and (../vlanType='common' or ../vlanType='seperate') ) or (../vlanType='sub' and (../vlanType='common' or ../vlanType='sub') ) or (../vlanType='super' and (../vlanType='common' or ../vlanType='super') ) or not(../vlanType!='common' and ../vlanType!='super' and ../vlanType!='sub' and ../vlanType!='principal' and ../vlanType!='group' and ../vlanType!='seperate' or ../vlanType='common' or ../vlanType='group' or ../vlanType='principal' or ../vlanType='seperate' or ../vlanType='sub' or ../vlanType='super')";
          default "common";
          description
            "VLAN type, such as common VLANs, super VLANs, and sub-VLANs. ";
        }
        leaf adminStatus {
          type vlanAdmin;
          must "not(../vlanType='carrier' or ../vlanType='fcoe')";
          default "up";
          description
            "Administrative status of a VLAN.";
          ext:allowDelete "true";
        }
        leaf subVlans {
          when "../vlanType='super'";
          type pub-type:VLAN_RANGE {
            length "0..9682";
          }
          description
            "List of sub-VLANs.";
          ext:allowDelete "true";
        }
        leaf superVlan {
          type vlanId {
            range "1..4094";
          }
          config false;
          description
            "The Corresponding Super-VLAN ID When the VLAN is a Sub-VLAN.";
          ext:allowDelete "true";
        }
        container vlanif {
          when "not(../vlanType!='common' and ../vlanType!='super' and ../vlanType!='principal')";
          description
            "VLANIF interface.";
          leaf ifName {
            type pub-type:ifName;
            config false;
            description
              "VLANIF interface name.";
          }
          leaf cfgBand {
            type uint32 {
              range "1..1000000";
            }
            description
              "VLANIF interface bandwidth, in Mbit/s.";
            ext:allowDelete "true";
          }
          leaf dampTime {
            type uint16 {
              range "0..20";
            }
            description
              "Delay time after which a VLANIF interface goes Down, in seconds.";
            ext:allowDelete "true";
          }
        }
        container muxVlan {
          when "../vlanType='principal'";
          description
            "Subordinate VLAN List";
          leaf separateVlan {
            type vlanId {
              range "1..4094";
            }
            description
              "Separate VLAN";
            ext:allowDelete "true";
          }
          leaf groupVlans {
            type pub-type:VLAN_RANGE {
              length "0..9682";
            }
            description
              "Group VLAN";
            ext:allowDelete "true";
            ext:allowDelete "true";
          }
        }
        container protocolVlans {
          description
            "protocol VLAN List.";
          list protocolVlan {
            when "not(../../vlanType='carrier' or ../../vlanType='fcoe')";
            key "protocolIndex protocolType";
            description
              "protocol VLAN.";
            leaf protocolIndex {
              type int16 {
                range "0..15";
              }
              description
                "protocol ifindex.";
            }
            leaf protocolType {
              type protocolVlanType;
              description
                "protocol Def.";
            }
            leaf encapType {
              when "not(../protocolType='at' or ../protocolType='ipv4' or ../protocolType='ipv6' or ../protocolType='ipx_ethernetii' or ../protocolType='ipx_llc' or ../protocolType='ipx_raw' or ../protocolType='ipx_snap' or not(../protocolType)) or ../protocolType='mode'";
              type encapType;
              mandatory true;
              description
                "protocol Encap Type.";
            }
            leaf snapProtocolValue {
              when "not(../encapType='llc' and ../protocolType='mode' or ../protocolType='at' or ../protocolType='ipv4' or ../protocolType='ipv6' or ../protocolType='ipx_ethernetii' or ../protocolType='ipx_llc' or ../protocolType='ipx_raw' or ../protocolType='ipx_snap' or ../protocolType='mode' and ../encapType='ethernetii' or ../protocolType='mode' or not(../protocolType)) or ../encapType='snap' and ../protocolType='mode'";
              type pub-type:hexBinary;
              mandatory true;
              description
                "snap Protocol Value.";
            }
            leaf ethiiProtocolValue {
              when "not(../encapType='llc' and ../protocolType='mode' or ../encapType='snap' and ../protocolType='mode' or ../protocolType='at' or ../protocolType='ipv4' or ../protocolType='ipv6' or ../protocolType='ipx_ethernetii' or ../protocolType='ipx_llc' or ../protocolType='ipx_raw' or ../protocolType='ipx_snap' or ../protocolType='mode' or not(../protocolType)) or ../protocolType='mode' and ../encapType='ethernetii'";
              type pub-type:hexBinary;
              mandatory true;
              description
                "ethii Protocol Value.";
            }
            leaf dsap {
              when "not(../encapType='snap' and ../protocolType='mode' or ../protocolType='at' or ../protocolType='ipv4' or ../protocolType='ipv6' or ../protocolType='ipx_ethernetii' or ../protocolType='ipx_llc' or ../protocolType='ipx_raw' or ../protocolType='ipx_snap' or ../protocolType='mode' and ../encapType='ethernetii' or ../protocolType='mode' or not(../protocolType)) or ../encapType='llc' and ../protocolType='mode'";
              type pub-type:hexBinary;
              mandatory true;
              description
                "dsap Value.";
            }
            leaf ssap {
              when "not(../encapType='snap' and ../protocolType='mode' or ../protocolType='at' or ../protocolType='ipv4' or ../protocolType='ipv6' or ../protocolType='ipx_ethernetii' or ../protocolType='ipx_llc' or ../protocolType='ipx_raw' or ../protocolType='ipx_snap' or ../protocolType='mode' and ../encapType='ethernetii' or ../protocolType='mode' or not(../protocolType)) or ../encapType='llc' and ../protocolType='mode'";
              type pub-type:hexBinary;
              mandatory true;
              description
                "ssap Value.";
            }
          }
        }
        container portInfos {
          config false;
          description
            "List of ports in a VLAN.";
          list portInfo {
            key "ifName";
            config false;
            description
              "Port in a VLAN.";
            leaf ifName {
              type pub-type:ifName;
              config false;
              description
                "Names of ports in a VLAN.";
            }
            leaf accessType {
              type vlanAccessType;
              config false;
              description
                "Port link type.";
            }
            leaf tagMode {
              type tagMode;
              config false;
              description
                "Port tag Mode.";
            }
          }
        }
      }
    }
    container dynamicVlans {
      config false;
      description
        "Dynamic VLAN List.";
      list dynamicVlan {
        key "vlanId";
        config false;
        max-elements  "4094";
        description
          "Dynamic VLAN.";
        leaf vlanId {
          type vlanId {
            range "1..4094";
          }
          config false;
          description
            "VLAN ID.";
        }
        leaf vlanDesc {
          type string {
            length "1..80";
          }
          config false;
          description
            "VLAN description.";
        }
        leaf adminStatus {
          type vlanAdmin;
          default "up";
          config false;
          description
            "Administrative status of a VLAN.";
        }
        container activePortInfos {
          config false;
          description
            "List of active ports in a dynamic VLAN.";
          list activePortInfo {
            key "ifName";
            config false;
            description
              "Active port in a dynamic VLAN.";
            leaf ifName {
              type pub-type:ifName;
              config false;
              description
                "Names of ports in a VLAN.";
            }
            leaf accessType {
              type vlanAccessType;
              config false;
              description
                "Port link type.";
            }
            leaf tagMode {
              type tagMode;
              config false;
              description
                "Port tag Mode.";
            }
          }
        }
      }
    }
    container instances {
      config false;
      description
        "Instances.";
      list instance {
        key "instanceId";
        config false;
        description
          "Instances.";
        leaf instanceId {
          type uint16 {
            range "0..4094";
          }
          config false;
          description
            "Instance ID.";
        }
        leaf instanceType {
          type instanceType;
          config false;
          mandatory true;
          description
            "instance type.";
        }
        leaf vlans {
          type pub-type:VLAN_RANGE {
            length "0..9682";
          }
          config false;
          mandatory true;
          description
            "VLAN list.";
        }
      }
    }
  }
}
