/*
Copyright (C) 2013-2017 Huawei Technologies Co., Ltd. All rights reserved.
*/
submodule huawei-ifmtrunk-action {
  belongs-to huawei-ifmtrunk {
    prefix ifmtrunk;
  }
  import huawei-pub-type {
    prefix pub-type;
  }
  include huawei-ifmtrunk-type;
  
  organization
    "Huawei Technologies Co.,Ltd.";
  contact
    "Huawei Industrial Base Bantian, Longgang Shenzhen 518129                    
        People's Republic of China                    
        Website: http://www.huawei.com Email: support@huawei.com";
  description
    "the ifmtrunk action submodule";
  revision 2017-03-23 {
    description
      "Functions supported by the schema are added to the YANG file.";
    reference
      "Huawei private.";
  }
  revision 2013-01-01 {
    description
      "Init revision";
    reference
      "Huawei private.";
  }
  rpc rstLacpTrunkCnt {
    description
      "Reset LACP PDU statistics.";
    input {
      leaf ifName {
        type pub-type:ifName;
        mandatory true;
        description
          "Trunk interface name.";
      }
    }
  }
  rpc rstLacpPortCnt {
    description
      "Reset LACP PDU statistics.";
    input {
      leaf ifName {
        type pub-type:ifName;
        mandatory true;
        description
          "Interface name.";
      }
    }
  }
}
