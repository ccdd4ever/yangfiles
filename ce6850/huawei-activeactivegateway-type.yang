/*
Copyright (C) 2013-2017 Huawei Technologies Co., Ltd. All rights reserved.
*/
submodule huawei-activeactivegateway-type {
  belongs-to huawei-activeactivegateway {
    prefix activeactivegateway;
  }
  
  organization
    "Huawei Technologies Co.,Ltd.";
  contact
    "Huawei Industrial Base Bantian, Longgang Shenzhen 518129                    
        People's Republic of China                    
        Website: http://www.huawei.com Email: support@huawei.com";
  description
    "ActiveGatewayType";
  revision 2017-03-23 {
    description
      "Functions supported by the schema are added to the YANG file.";
    reference
      "Huawei private.";
  }
  revision 2013-01-01 {
    description
      "Init revision";
    reference
      "Huawei private.";
  }
  typedef state {
    type enumeration {
      enum "Inactive" {
        description
          "Inactive.";
      }
      enum "Active" {
        description
          "Active.";
      }
    }
    description
      "";
  }
}
