/*
Copyright (C) 2013-2017 Huawei Technologies Co., Ltd. All rights reserved.
*/
submodule huawei-nsm-action {
  belongs-to huawei-nsm {
    prefix nsm;
  }
  import huawei-pub-type {
    prefix pub-type;
  }
  include huawei-nsm-type;
  
  organization
    "Huawei Technologies Co.,Ltd.";
  contact
    "Huawei Industrial Base Bantian, Longgang Shenzhen 518129                    
        People's Republic of China                    
        Website: http://www.huawei.com Email: support@huawei.com";
  description
    "nsm action:";
  revision 2017-03-23 {
    description
      "Functions supported by the schema are added to the YANG file.";
    reference
      "Huawei private.";
  }
  revision 2013-01-01 {
    description
      "Init revision";
    reference
      "Huawei private.";
  }
  rpc nsmResetCache {
    description
      "Reset Cache.";
    input {
      leaf flowType {
        type uint32;
        description
          "Flow type. The value can be 0 or 1.";
      }
      leaf slot {
        type pub-type:slotPath;
        description
          "Board ID.";
      }
      leaf cache {
        type uint32;
        description
          "Cache.";
      }
    }
  }
  rpc nsmResetStat {
    description
      "Reset State.";
    input {
      leaf flowType {
        type uint32;
        description
          "Flow type. The value can be 0 or 1.";
      }
      leaf slot {
        type pub-type:slotPath;
        description
          "Board ID.";
      }
      leaf resetstatistics {
        type uint32;
        description
          "Reset Statistics.";
      }
    }
  }
}
