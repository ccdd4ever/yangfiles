/*
Copyright (C) 2013-2017 Huawei Technologies Co., Ltd. All rights reserved.
*/
submodule huawei-dsa-type {
  belongs-to huawei-dsa {
    prefix dsa;
  }
  
  organization
    "Huawei Technologies Co.,Ltd.";
  contact
    "Huawei Industrial Base Bantian, Longgang Shenzhen 518129                    
        People's Republic of China                    
        Website: http://www.huawei.com Email: support@huawei.com";
  description
    "Description of dsa type submodule";
  revision 2017-03-23 {
    description
      "Functions supported by the schema are added to the YANG file.";
    reference
      "Huawei private.";
  }
  revision 2013-01-01 {
    description
      "Init revision";
    reference
      "Huawei private.";
  }
  typedef dsaDSAKeyType {
    type enumeration {
      enum "2048" {
        description
          "Modulus 2048";
      }
    }
    description
      "Dsa key length";
  }
  typedef dsaEncodeInType {
    type enumeration {
      enum "DER" {
        description
          "DER";
      }
      enum "PEM" {
        description
          "PEM";
      }
      enum "OPENSSH" {
        description
          "OPENSSH";
      }
    }
    description
      "DSA encodein type list";
  }
}
