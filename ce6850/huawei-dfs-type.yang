submodule huawei-dfs-type {
    belongs-to "huawei-dfs" {
        prefix "dfs";
    }
    
    organization "Huawei Technologies Co.,Ltd.";
    contact "Huawei Industrial Base Bantian, Longgang Shenzhen 518129                    
              People's Republic of China                    
              Website: http://www.huawei.com Email: support@huawei.com";
  revision 2017-03-23 {
    description
      "Functions supported by the schema are added to the YANG file.";
    reference
      "Huawei private.";
  }
  revision 2013-01-01 {
    description
      "Init revision";
    reference
      "Huawei private.";
  }
    typedef udpPortState {
        description "";
        type enumeration {
            enum "active" {
                value 0;
                description "Active.";
            }
            enum "duplicated" {
                value 1;
                description "Duplicated.";
            }
        }
    }
    typedef addressType {
        description "";
        type enumeration {
            enum "IPV4" {
                value 0;
                description "IPV4";
            }
            enum "IPV6" {
                value 1;
                description "IPV6";
            }
        }
    }
}
