/*
Copyright (C) 2013-2017 Huawei Technologies Co., Ltd. All rights reserved.
*/
submodule huawei-fm-action {
  belongs-to huawei-fm {
    prefix fm;
  }
  include huawei-fm-type;
  
  organization
    "Huawei Technologies Co.,Ltd.";
  contact
    "Huawei Industrial Base Bantian, Longgang Shenzhen 518129                    
        People's Republic of China                    
        Website: http://www.huawei.com Email: support@huawei.com";
  description
    "Description of fm action submodule";
  revision 2017-03-23 {
    description
      "Functions supported by the schema are added to the YANG file.";
    reference
      "Huawei private.";
  }
  revision 2013-01-01 {
    description
      "Init revision";
    reference
      "Huawei private.";
  }
  rpc clearAllHistory {
    description
      "Clear all historical alarms.";
  }
  rpc clearHistory {
    description
      "Clear historical alarms by sequence.";
    input {
      leaf alarmSequence {
        type uint32;
        description
          "Sequence number of an alarm.";
      }
    }
  }
}
